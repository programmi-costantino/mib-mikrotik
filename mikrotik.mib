MIKROTIK-MIB DEFINITIONS ::= BEGIN

IMPORTS
InetAddressType, InetAddress, InetPortNumber FROM INET-ADDRESS-MIB
MODULE-IDENTITY, OBJECT-TYPE, Integer32, Counter32, Gauge32, IpAddress,
Counter64, Unsigned32, enterprises, NOTIFICATION-TYPE, TimeTicks FROM SNMPv2-SMI
TEXTUAL-CONVENTION, DisplayString, MacAddress, TruthValue, DateAndTime FROM SNMPv2-TC
OBJECT-GROUP, NOTIFICATION-GROUP FROM SNMPv2-CONF;

mikrotikExperimentalModule MODULE-IDENTITY
  LAST-UPDATED "202607070000Z"
  ORGANIZATION "MikroTik"
  CONTACT-INFO "support@mikrotik.com"
  DESCRIPTION
      "MikroTik RouterOS enterprise MIB: wireless, queues, health,
       licensing, hotspot, DHCP, system, scripts, neighbors, GPS,
       modems, interface statistics, PoE, LTE, partitions, optical
       modules, IPsec, WiFi (CAPsMAN) and connection tracking."
  REVISION "202607070000Z"
  DESCRIPTION
      "Current revision, with descriptions and units for all objects."
  ::= { mikrotik 1 }

mikrotik OBJECT IDENTIFIER ::= { enterprises 14988 }
mtXMetaInfo OBJECT IDENTIFIER ::= { mikrotikExperimentalModule 2 }
mtXRouterOsGroups OBJECT IDENTIFIER ::= { mtXMetaInfo 1 }

mtXRouterOs OBJECT IDENTIFIER ::= { mikrotikExperimentalModule 1 }
mtxrWireless OBJECT IDENTIFIER ::= { mtXRouterOs 1 }
mtxrQueues OBJECT IDENTIFIER ::= { mtXRouterOs 2 }
mtxrHealth OBJECT IDENTIFIER ::= { mtXRouterOs 3 }
mtxrLicense OBJECT IDENTIFIER ::= { mtXRouterOs 4 }
mtxrHotspot OBJECT IDENTIFIER ::= { mtXRouterOs 5 }
mtxrDHCP OBJECT IDENTIFIER ::= { mtXRouterOs 6 }
mtxrSystem OBJECT IDENTIFIER ::= { mtXRouterOs 7 }
mtxrScripts OBJECT IDENTIFIER ::= { mtXRouterOs 8 }
mtxrTraps OBJECT IDENTIFIER ::= { mtXRouterOs 9 }
mtxrNstremeDual OBJECT IDENTIFIER ::= { mtXRouterOs 10 }
mtxrNeighbor OBJECT IDENTIFIER ::= { mtXRouterOs 11 }
mtxrGps OBJECT IDENTIFIER ::= { mtXRouterOs 12 }
mtxrWirelessModem OBJECT IDENTIFIER ::= { mtXRouterOs 13 }
mtxrInterfaceStats OBJECT IDENTIFIER ::= { mtXRouterOs 14 }
mtxrPOE OBJECT IDENTIFIER ::= { mtXRouterOs 15 }
mtxrLTEModem OBJECT IDENTIFIER ::= { mtXRouterOs 16 }
mtxrPartition OBJECT IDENTIFIER ::= { mtXRouterOs 17 }
mtxrScriptRun OBJECT IDENTIFIER ::= { mtXRouterOs 18 }
mtxrOptical OBJECT IDENTIFIER ::= { mtXRouterOs 19 }
mtxrIPSec OBJECT IDENTIFIER ::= { mtXRouterOs 20 }
mtxrWifi OBJECT IDENTIFIER ::= { mtXRouterOs 21 }
mtxrCT OBJECT IDENTIFIER ::= { mtXRouterOs 22 }

ObjectIndex ::= TEXTUAL-CONVENTION
    DISPLAY-HINT "x"
    STATUS current
    DESCRIPTION
        "Internal RouterOS object ID used as a table index. It is not the item number shown by the console print command."
    SYNTAX Integer32 (0..2147483647)
-- Note that actually in RouterOs index values can be in range 0..4294967294,
-- this can sometimes make them negative. Any of the following syntaxes would
-- be more appropriate, but since Integer32 is used for InterfaceIndex in
-- IF-MIB, where it can also take negative values in RouterOs, it is used
-- here for consistency.
-- Also note that ObjectIndex value is not related to item numbers that are
-- used by console and shown by console print command.
--
-- SYNTAX Integer32 (-2147483648..2147483647)
-- SYNTAX Unsigned32 (0..4294967295)

HexInt ::= TEXTUAL-CONVENTION
    DISPLAY-HINT "x"
    STATUS current
    DESCRIPTION "Integer displayed in hexadecimal."
    SYNTAX Integer32 (-2147483648..2147483647)

Voltage ::= TEXTUAL-CONVENTION
    DISPLAY-HINT "d-1"
    STATUS current
    DESCRIPTION
        "Voltage in volts, stored as tenths of a volt (0.1 V resolution)."
    SYNTAX Integer32 (-2147483648..2147483647)

Temperature ::= TEXTUAL-CONVENTION
    DISPLAY-HINT "d-1"
    STATUS current
    DESCRIPTION
        "Temperature in degrees Celsius, stored as tenths of a degree (0.1 C resolution)."
    SYNTAX Integer32 (-2147483648..2147483647)

Power ::= TEXTUAL-CONVENTION
    DISPLAY-HINT "d-1"
    STATUS current
    DESCRIPTION
        "Power in watts, stored as tenths of a watt (0.1 W resolution)."
    SYNTAX Integer32 (-2147483648..2147483647)

GDiv100 ::= TEXTUAL-CONVENTION
    DISPLAY-HINT "d-2"
    STATUS current
    DESCRIPTION
        "Unsigned value stored multiplied by 100 (two implied decimals)."
    SYNTAX Gauge32

GDiv1000 ::= TEXTUAL-CONVENTION
    DISPLAY-HINT "d-3"
    STATUS current
    DESCRIPTION
        "Unsigned value stored multiplied by 1000 (three implied decimals)."
    SYNTAX Gauge32

IDiv10 ::= TEXTUAL-CONVENTION
    DISPLAY-HINT "d-1"
    STATUS current
    DESCRIPTION
        "Signed value stored multiplied by 10 (one implied decimal)."
    SYNTAX Integer32 (-2147483648..2147483647)

IDiv1000 ::= TEXTUAL-CONVENTION
    DISPLAY-HINT "d-3"
    STATUS current
    DESCRIPTION
        "Signed value stored multiplied by 1000 (three implied decimals)."
    SYNTAX Integer32 (-2147483648..2147483647)

BoolValue ::= TEXTUAL-CONVENTION
    STATUS       current
    DESCRIPTION
    "Boolean value."
    SYNTAX       INTEGER { false(0), true(1) }

IsakmpCookie ::= TEXTUAL-CONVENTION
    DISPLAY-HINT    "16a"
    STATUS          current
    DESCRIPTION "ISAKMP cookie string"
    SYNTAX  OCTET STRING (SIZE (16))

-- WIRELESS ********************************************************************

mtxrWlStatTable OBJECT-TYPE
    SYNTAX SEQUENCE OF MtxrWlStatEntry
    MAX-ACCESS not-accessible
    STATUS current
    DESCRIPTION "Table of wireless station-mode interface entries."
    ::= { mtxrWireless 1 }

mtxrWlStatEntry OBJECT-TYPE
    SYNTAX MtxrWlStatEntry
    MAX-ACCESS not-accessible
    STATUS current
    DESCRIPTION "Wireless station mode interface."
    INDEX { mtxrWlStatIndex }
    ::= { mtxrWlStatTable 1 }

MtxrWlStatEntry ::= SEQUENCE {
    mtxrWlStatIndex ObjectIndex,
    mtxrWlStatTxRate Gauge32,
    mtxrWlStatRxRate Gauge32,
    mtxrWlStatStrength Integer32,
    mtxrWlStatSsid DisplayString,
    mtxrWlStatBssid MacAddress,
    mtxrWlStatFreq Integer32,
    mtxrWlStatBand DisplayString,
    mtxrWlStatTxCCQ Counter32,
    mtxrWlStatRxCCQ Counter32
}

mtxrWlStatIndex OBJECT-TYPE
    SYNTAX ObjectIndex
    MAX-ACCESS not-accessible
    STATUS current
    DESCRIPTION
        "Index identifying the row (internal object ID, not the console
         item number)."
    ::= { mtxrWlStatEntry 1 }

mtxrWlStatTxRate OBJECT-TYPE
    SYNTAX Gauge32
    UNITS "bits per second"
    MAX-ACCESS read-only
    STATUS current
    DESCRIPTION "Transmit rate (wireless station-mode interface)."
    ::= { mtxrWlStatEntry 2 }

mtxrWlStatRxRate OBJECT-TYPE
    SYNTAX Gauge32
    UNITS "bits per second"
    MAX-ACCESS read-only
    STATUS current
    DESCRIPTION "Receive rate (wireless station-mode interface)."
    ::= { mtxrWlStatEntry 3 }

mtxrWlStatStrength OBJECT-TYPE
    SYNTAX Integer32
    UNITS "dBm"
    MAX-ACCESS read-only
    STATUS current
    DESCRIPTION "Signal strength (wireless station-mode interface)."
    ::= { mtxrWlStatEntry 4 }

mtxrWlStatSsid OBJECT-TYPE
    SYNTAX DisplayString
    MAX-ACCESS read-only
    STATUS current
    DESCRIPTION "SSID (wireless station-mode interface)."
    ::= { mtxrWlStatEntry 5 }

mtxrWlStatBssid OBJECT-TYPE
    SYNTAX MacAddress
    MAX-ACCESS read-only
    STATUS current
    DESCRIPTION "BSSID (wireless station-mode interface)."
    ::= { mtxrWlStatEntry 6 }

mtxrWlStatFreq OBJECT-TYPE
    SYNTAX Integer32
    UNITS "MHz"
    MAX-ACCESS read-only
    STATUS current
    DESCRIPTION "Frequency (wireless station-mode interface)."
    ::= { mtxrWlStatEntry 7 }

mtxrWlStatBand OBJECT-TYPE
    SYNTAX DisplayString
    MAX-ACCESS read-only
    STATUS current
    DESCRIPTION "Band (wireless station-mode interface)."
    ::= { mtxrWlStatEntry 8 }

mtxrWlStatTxCCQ OBJECT-TYPE
    SYNTAX Counter32
    UNITS "%"
    MAX-ACCESS read-only
    STATUS current
    DESCRIPTION "Transmit CCQ (wireless station-mode interface)."
    ::= { mtxrWlStatEntry 9 }

mtxrWlStatRxCCQ OBJECT-TYPE
    SYNTAX Counter32
    UNITS "%"
    MAX-ACCESS read-only
    STATUS current
    DESCRIPTION "Receive CCQ (wireless station-mode interface)."
    ::= { mtxrWlStatEntry 10 }

-- WlRtabTable
mtxrWlRtabTable OBJECT-TYPE
    SYNTAX SEQUENCE OF MtxrWlRtabEntry
    MAX-ACCESS not-accessible
    STATUS current
    DESCRIPTION "Table of wireless registration table entries."
    ::= { mtxrWireless 2 }

mtxrWlRtabEntry OBJECT-TYPE
    SYNTAX MtxrWlRtabEntry
    MAX-ACCESS not-accessible
    STATUS current
    DESCRIPTION
        "Wireless registration table. It is indexed by remote mac-address
         and local interface index."
    INDEX { mtxrWlRtabAddr, mtxrWlRtabIface }
    ::= { mtxrWlRtabTable 1 }

MtxrWlRtabEntry ::= SEQUENCE {
    mtxrWlRtabAddr MacAddress,
    mtxrWlRtabIface ObjectIndex,
    mtxrWlRtabStrength Integer32,
    mtxrWlRtabTxBytes Counter32,
    mtxrWlRtabRxBytes Counter32,
    mtxrWlRtabTxPackets Counter32,
    mtxrWlRtabRxPackets Counter32,
    mtxrWlRtabTxRate Gauge32,
    mtxrWlRtabRxRate Gauge32,
    mtxrWlRtabRouterOSVersion DisplayString,
    mtxrWlRtabUptime TimeTicks,
    mtxrWlRtabSignalToNoise Integer32,
    mtxrWlRtabTxStrengthCh0 Integer32,
    mtxrWlRtabRxStrengthCh0 Integer32,
    mtxrWlRtabTxStrengthCh1 Integer32,
    mtxrWlRtabRxStrengthCh1 Integer32,
    mtxrWlRtabTxStrengthCh2 Integer32,
    mtxrWlRtabRxStrengthCh2 Integer32,
    mtxrWlRtabTxStrength Integer32,
    mtxrWlRtabRadioName DisplayString
}

mtxrWlRtabAddr OBJECT-TYPE
    SYNTAX MacAddress
    MAX-ACCESS not-accessible
    STATUS current
    DESCRIPTION "MAC address of the remote device."
    ::= { mtxrWlRtabEntry 1 }

mtxrWlRtabIface OBJECT-TYPE
    SYNTAX ObjectIndex
    MAX-ACCESS not-accessible
    STATUS current
    DESCRIPTION
        "Index of the local wireless interface the client is registered on."
    ::= { mtxrWlRtabEntry 2 }

mtxrWlRtabStrength OBJECT-TYPE
    SYNTAX Integer32
    UNITS "dBm"
    MAX-ACCESS read-only
    STATUS current
    DESCRIPTION
        "Signal strength of the remote client as received by the local
         radio."
    ::= { mtxrWlRtabEntry 3 }

mtxrWlRtabTxBytes OBJECT-TYPE
    SYNTAX Counter32
    UNITS "bytes"
    MAX-ACCESS read-only
    STATUS current
    DESCRIPTION "Transmit bytes (wireless registration table)."
    ::= { mtxrWlRtabEntry 4 }

mtxrWlRtabRxBytes OBJECT-TYPE
    SYNTAX Counter32
    UNITS "bytes"
    MAX-ACCESS read-only
    STATUS current
    DESCRIPTION "Receive bytes (wireless registration table)."
    ::= { mtxrWlRtabEntry 5 }

mtxrWlRtabTxPackets OBJECT-TYPE
    SYNTAX Counter32
    UNITS "packets"
    MAX-ACCESS read-only
    STATUS current
    DESCRIPTION "Transmit packets (wireless registration table)."
    ::= { mtxrWlRtabEntry 6 }

mtxrWlRtabRxPackets OBJECT-TYPE
    SYNTAX Counter32
    UNITS "packets"
    MAX-ACCESS read-only
    STATUS current
    DESCRIPTION "Receive packets (wireless registration table)."
    ::= { mtxrWlRtabEntry 7 }

mtxrWlRtabTxRate OBJECT-TYPE
    SYNTAX Gauge32
    UNITS "bits per second"
    MAX-ACCESS read-only
    STATUS current
    DESCRIPTION "Transmit rate (wireless registration table)."
    ::= { mtxrWlRtabEntry 8 }

mtxrWlRtabRxRate OBJECT-TYPE
    SYNTAX Gauge32
    UNITS "bits per second"
    MAX-ACCESS read-only
    STATUS current
    DESCRIPTION "Receive rate (wireless registration table)."
    ::= { mtxrWlRtabEntry 9 }

mtxrWlRtabRouterOSVersion OBJECT-TYPE
    SYNTAX DisplayString
    MAX-ACCESS read-only
    STATUS current
    DESCRIPTION "RouterOS version."
    ::= { mtxrWlRtabEntry 10 }

mtxrWlRtabUptime OBJECT-TYPE
    SYNTAX TimeTicks
    MAX-ACCESS read-only
    STATUS current
    DESCRIPTION "Uptime."
    ::= { mtxrWlRtabEntry 11 }

mtxrWlRtabSignalToNoise OBJECT-TYPE
    SYNTAX Integer32
    UNITS "dB"
    MAX-ACCESS read-only
    STATUS current
    DESCRIPTION "Signal-to-noise ratio. 0 means the value is not available."
    ::= { mtxrWlRtabEntry 12 }

mtxrWlRtabTxStrengthCh0 OBJECT-TYPE
    SYNTAX Integer32
    UNITS "dBm"
    MAX-ACCESS read-only
    STATUS current
    DESCRIPTION
        "Transmit signal strength ch0 (wireless registration table)."
    ::= { mtxrWlRtabEntry 13 }

mtxrWlRtabRxStrengthCh0 OBJECT-TYPE
    SYNTAX Integer32
    UNITS "dBm"
    MAX-ACCESS read-only
    STATUS current
    DESCRIPTION "Receive signal strength ch0 (wireless registration table)."
    ::= { mtxrWlRtabEntry 14 }

mtxrWlRtabTxStrengthCh1 OBJECT-TYPE
    SYNTAX Integer32
    UNITS "dBm"
    MAX-ACCESS read-only
    STATUS current
    DESCRIPTION
        "Transmit signal strength ch1 (wireless registration table)."
    ::= { mtxrWlRtabEntry 15 }

mtxrWlRtabRxStrengthCh1 OBJECT-TYPE
    SYNTAX Integer32
    UNITS "dBm"
    MAX-ACCESS read-only
    STATUS current
    DESCRIPTION "Receive signal strength ch1 (wireless registration table)."
    ::= { mtxrWlRtabEntry 16 }

mtxrWlRtabTxStrengthCh2 OBJECT-TYPE
    SYNTAX Integer32
    UNITS "dBm"
    MAX-ACCESS read-only
    STATUS current
    DESCRIPTION
        "Transmit signal strength ch2 (wireless registration table)."
    ::= { mtxrWlRtabEntry 17 }

mtxrWlRtabRxStrengthCh2 OBJECT-TYPE
    SYNTAX Integer32
    UNITS "dBm"
    MAX-ACCESS read-only
    STATUS current
    DESCRIPTION "Receive signal strength ch2 (wireless registration table)."
    ::= { mtxrWlRtabEntry 18 }

mtxrWlRtabTxStrength OBJECT-TYPE
    SYNTAX Integer32
    UNITS "dBm"
    MAX-ACCESS read-only
    STATUS current
    DESCRIPTION
        "Overall signal strength of frames transmitted to the remote
         client."
    ::= { mtxrWlRtabEntry 19 }

mtxrWlRtabRadioName OBJECT-TYPE
    SYNTAX DisplayString
    MAX-ACCESS read-only
    STATUS current
    DESCRIPTION "Radio name (wireless registration table)."
    ::= { mtxrWlRtabEntry 20 }

mtxrWlRtabEntryCount OBJECT-TYPE
    SYNTAX Gauge32
    MAX-ACCESS read-only
    STATUS current
    DESCRIPTION "Number of entries in the wireless registration table."
    ::= { mtxrWireless 4 }

mtxrWlApTable OBJECT-TYPE
    SYNTAX SEQUENCE OF MtxrWlApEntry
    MAX-ACCESS not-accessible
    STATUS current
    DESCRIPTION "Table of wireless access-point interface entries."
    ::= { mtxrWireless 3 }

mtxrWlApEntry OBJECT-TYPE
    SYNTAX MtxrWlApEntry
    MAX-ACCESS not-accessible
    STATUS current
    DESCRIPTION "Wireless access point mode interface."
    INDEX { mtxrWlApIndex }
    ::= { mtxrWlApTable 1 }

MtxrWlApEntry ::= SEQUENCE {
    mtxrWlApIndex ObjectIndex,
    mtxrWlApTxRate Gauge32,
    mtxrWlApRxRate Gauge32,
    mtxrWlApSsid DisplayString,
    mtxrWlApBssid MacAddress,
    mtxrWlApClientCount Counter32,
    mtxrWlApFreq Integer32,
    mtxrWlApBand DisplayString,
    mtxrWlApNoiseFloor Integer32,
    mtxrWlApOverallTxCCQ Counter32,
    mtxrWlApAuthClientCount Counter32
}

mtxrWlApIndex OBJECT-TYPE
    SYNTAX ObjectIndex
    MAX-ACCESS not-accessible
    STATUS current
    DESCRIPTION
        "Index identifying the row (internal object ID, not the console
         item number)."
    ::= { mtxrWlApEntry 1 }

mtxrWlApTxRate OBJECT-TYPE
    SYNTAX Gauge32
    UNITS "bits per second"
    MAX-ACCESS read-only
    STATUS current
    DESCRIPTION "Transmit rate (wireless access-point interface)."
    ::= { mtxrWlApEntry 2 }

mtxrWlApRxRate OBJECT-TYPE
    SYNTAX Gauge32
    UNITS "bits per second"
    MAX-ACCESS read-only
    STATUS current
    DESCRIPTION "Receive rate (wireless access-point interface)."
    ::= { mtxrWlApEntry 3 }

mtxrWlApSsid OBJECT-TYPE
    SYNTAX DisplayString
    MAX-ACCESS read-only
    STATUS current
    DESCRIPTION "SSID (wireless access-point interface)."
    ::= { mtxrWlApEntry 4 }

mtxrWlApBssid OBJECT-TYPE
    SYNTAX MacAddress
    MAX-ACCESS read-only
    STATUS current
    DESCRIPTION "BSSID (wireless access-point interface)."
    ::= { mtxrWlApEntry 5 }

mtxrWlApClientCount OBJECT-TYPE
    SYNTAX Counter32
    MAX-ACCESS read-only
    STATUS current
    DESCRIPTION "Client count (wireless access-point interface)."
    ::= { mtxrWlApEntry 6 }

mtxrWlApFreq OBJECT-TYPE
    SYNTAX Integer32
    UNITS "MHz"
    MAX-ACCESS read-only
    STATUS current
    DESCRIPTION "Frequency (wireless access-point interface)."
    ::= { mtxrWlApEntry 7 }

mtxrWlApBand OBJECT-TYPE
    SYNTAX DisplayString
    MAX-ACCESS read-only
    STATUS current
    DESCRIPTION "Band (wireless access-point interface)."
    ::= { mtxrWlApEntry 8 }

mtxrWlApNoiseFloor OBJECT-TYPE
    SYNTAX Integer32
    UNITS "dBm"
    MAX-ACCESS read-only
    STATUS current
    DESCRIPTION "Noise floor (wireless access-point interface)."
    ::= { mtxrWlApEntry 9 }

mtxrWlApOverallTxCCQ OBJECT-TYPE
    SYNTAX Counter32
    UNITS "%"
    MAX-ACCESS read-only
    STATUS current
    DESCRIPTION "Overall transmit CCQ (wireless access-point interface)."
    ::= { mtxrWlApEntry 10 }

mtxrWlApAuthClientCount OBJECT-TYPE
    SYNTAX Counter32
    MAX-ACCESS read-only
    STATUS current
    DESCRIPTION "Client count (wireless access-point interface)."
    ::= { mtxrWlApEntry 11 }

mtxrWlCMRtabTable OBJECT-TYPE
    SYNTAX SEQUENCE OF MtxrWlCMRtabEntry
    MAX-ACCESS not-accessible
    STATUS current
    DESCRIPTION "Table of CAPsMAN registration table entries."
    ::= { mtxrWireless 5 }

mtxrWlCMRtabEntry OBJECT-TYPE
    SYNTAX MtxrWlCMRtabEntry
    MAX-ACCESS not-accessible
    STATUS current
    DESCRIPTION
        "Wireless CAPSMAN registration table. It is indexed by remote mac-
         address and local interface index."
    INDEX { mtxrWlCMRtabAddr, mtxrWlCMRtabIface }
    ::= { mtxrWlCMRtabTable 1 }

MtxrWlCMRtabEntry ::= SEQUENCE {
    mtxrWlCMRtabAddr MacAddress,
    mtxrWlCMRtabIface ObjectIndex,
    mtxrWlCMRtabUptime TimeTicks,
    mtxrWlCMRtabTxBytes Counter32,
    mtxrWlCMRtabRxBytes Counter32,
    mtxrWlCMRtabTxPackets Counter32,
    mtxrWlCMRtabRxPackets Counter32,
    mtxrWlCMRtabTxRate Gauge32,
    mtxrWlCMRtabRxRate Gauge32,
    mtxrWlCMRtabTxStrength Integer32,
    mtxrWlCMRtabRxStrength Integer32,
    mtxrWlCMRtabSsid DisplayString,
    mtxrWlCMRtabEapIdent DisplayString
}

mtxrWlCMRtabAddr OBJECT-TYPE
    SYNTAX MacAddress
    MAX-ACCESS read-only
    STATUS current
    DESCRIPTION "MAC address of the remote device."
    ::= { mtxrWlCMRtabEntry 1 }
    -- should not be accessible in SMIv2

mtxrWlCMRtabIface OBJECT-TYPE
    SYNTAX ObjectIndex
    MAX-ACCESS not-accessible
    STATUS current
    DESCRIPTION
        "Index of the CAPsMAN interface the client is registered on."
    ::= { mtxrWlCMRtabEntry 2 }

mtxrWlCMRtabUptime OBJECT-TYPE
    SYNTAX TimeTicks
    MAX-ACCESS read-only
    STATUS current
    DESCRIPTION "Uptime."
    ::= { mtxrWlCMRtabEntry 3 }

mtxrWlCMRtabTxBytes OBJECT-TYPE
    SYNTAX Counter32
    UNITS "bytes"
    MAX-ACCESS read-only
    STATUS current
    DESCRIPTION "Transmit bytes (CAPsMAN registration table)."
    ::= { mtxrWlCMRtabEntry 4 }

mtxrWlCMRtabRxBytes OBJECT-TYPE
    SYNTAX Counter32
    UNITS "bytes"
    MAX-ACCESS read-only
    STATUS current
    DESCRIPTION "Receive bytes (CAPsMAN registration table)."
    ::= { mtxrWlCMRtabEntry 5 }

mtxrWlCMRtabTxPackets OBJECT-TYPE
    SYNTAX Counter32
    UNITS "packets"
    MAX-ACCESS read-only
    STATUS current
    DESCRIPTION "Transmit packets (CAPsMAN registration table)."
    ::= { mtxrWlCMRtabEntry 6 }

mtxrWlCMRtabRxPackets OBJECT-TYPE
    SYNTAX Counter32
    UNITS "packets"
    MAX-ACCESS read-only
    STATUS current
    DESCRIPTION "Receive packets (CAPsMAN registration table)."
    ::= { mtxrWlCMRtabEntry 7 }

mtxrWlCMRtabTxRate OBJECT-TYPE
    SYNTAX Gauge32
    UNITS "bits per second"
    MAX-ACCESS read-only
    STATUS current
    DESCRIPTION "Transmit rate (CAPsMAN registration table)."
    ::= { mtxrWlCMRtabEntry 8 }

mtxrWlCMRtabRxRate OBJECT-TYPE
    SYNTAX Gauge32
    UNITS "bits per second"
    MAX-ACCESS read-only
    STATUS current
    DESCRIPTION "Receive rate (CAPsMAN registration table)."
    ::= { mtxrWlCMRtabEntry 9 }

mtxrWlCMRtabTxStrength OBJECT-TYPE
    SYNTAX Integer32
    UNITS "dBm"
    MAX-ACCESS read-only
    STATUS current
    DESCRIPTION "Transmit signal strength (CAPsMAN registration table)."
    ::= { mtxrWlCMRtabEntry 10 }

mtxrWlCMRtabRxStrength OBJECT-TYPE
    SYNTAX Integer32
    UNITS "dBm"
    MAX-ACCESS read-only
    STATUS current
    DESCRIPTION "Receive signal strength (CAPsMAN registration table)."
    ::= { mtxrWlCMRtabEntry 11 }

mtxrWlCMRtabSsid OBJECT-TYPE
    SYNTAX DisplayString
    MAX-ACCESS read-only
    STATUS current
    DESCRIPTION "SSID (CAPsMAN registration table)."
    ::= { mtxrWlCMRtabEntry 12 }

mtxrWlCMRtabEapIdent OBJECT-TYPE
    SYNTAX DisplayString
    MAX-ACCESS read-only
    STATUS current
    DESCRIPTION "EAP identity (CAPsMAN registration table)."
    ::= { mtxrWlCMRtabEntry 13 }

mtxrWlCMRtabEntryCount OBJECT-TYPE
    SYNTAX Gauge32
    MAX-ACCESS read-only
    STATUS current
    DESCRIPTION "Number of entries in the CAPsMAN registration table."
    ::= { mtxrWireless 6 }

mtxrWlCMREntryCount OBJECT-TYPE
    SYNTAX Gauge32
    MAX-ACCESS read-only
    STATUS current
    DESCRIPTION "Number of remote CAPs known to the CAPsMAN."
    ::= { mtxrWireless 10 }

mtxrWlCMTable OBJECT-TYPE
    SYNTAX SEQUENCE OF MtxrWlCMEntry
    MAX-ACCESS not-accessible
    STATUS current
    DESCRIPTION "Table of CAPsMAN interface entries."
    ::= { mtxrWireless 7 }

mtxrWlCMEntry OBJECT-TYPE
    SYNTAX MtxrWlCMEntry
    MAX-ACCESS not-accessible
    STATUS current
    DESCRIPTION "CAPS-MAN mode interface."
    INDEX { mtxrWlCMIndex }
    ::= { mtxrWlCMTable 1 }

MtxrWlCMEntry ::= SEQUENCE {
    mtxrWlCMIndex ObjectIndex,
    mtxrWlCMRegClientCount Counter32,
    mtxrWlCMAuthClientCount Counter32,
    mtxrWlCMState DisplayString,
    mtxrWlCMChannel DisplayString
}

mtxrWlCMIndex OBJECT-TYPE
    SYNTAX ObjectIndex
    MAX-ACCESS not-accessible
    STATUS current
    DESCRIPTION
        "Index identifying the row (internal object ID, not the console
         item number)."
    ::= { mtxrWlCMEntry 1 }

mtxrWlCMRegClientCount OBJECT-TYPE
    SYNTAX Counter32
    MAX-ACCESS read-only
    STATUS current
    DESCRIPTION "Eg client count (CAPsMAN)."
    ::= { mtxrWlCMEntry 2 }

mtxrWlCMAuthClientCount OBJECT-TYPE
    SYNTAX Counter32
    MAX-ACCESS read-only
    STATUS current
    DESCRIPTION "Auth client count (CAPsMAN interface)."
    ::= { mtxrWlCMEntry 3 }

mtxrWlCMState OBJECT-TYPE
    SYNTAX DisplayString
    MAX-ACCESS read-only
    STATUS current
    DESCRIPTION "State (CAPsMAN interface)."
    ::= { mtxrWlCMEntry 4 }

mtxrWlCMChannel OBJECT-TYPE
    SYNTAX DisplayString
    MAX-ACCESS read-only
    STATUS current
    DESCRIPTION "For master only."
    ::= { mtxrWlCMEntry 5 }

--
mtxrWlCMRemoteTable OBJECT-TYPE
    SYNTAX SEQUENCE OF MtxrWlCMRemoteEntry
    MAX-ACCESS not-accessible
    STATUS current
    DESCRIPTION "Table of CAPsMAN remote CAP entries."
    ::= { mtxrWireless 11 }

mtxrWlCMRemoteEntry OBJECT-TYPE
    SYNTAX MtxrWlCMRemoteEntry
    MAX-ACCESS not-accessible
    STATUS current
    DESCRIPTION "CAPSMAN remote-cap list."
    INDEX { mtxrWlCMRemoteIndex }
    ::= { mtxrWlCMRemoteTable 1 }

MtxrWlCMRemoteEntry ::= SEQUENCE {
    mtxrWlCMRemoteIndex ObjectIndex,
    mtxrWlCMRemoteName DisplayString,
    mtxrWlCMRemoteState DisplayString,
    mtxrWlCMRemoteAddress DisplayString,
    mtxrWlCMRemoteRadios Counter32
}

mtxrWlCMRemoteIndex OBJECT-TYPE
    SYNTAX ObjectIndex
    MAX-ACCESS not-accessible
    STATUS current
    DESCRIPTION
        "Index identifying the row (internal object ID, not the console
         item number)."
    ::= { mtxrWlCMRemoteEntry 1 }

mtxrWlCMRemoteName OBJECT-TYPE
    SYNTAX DisplayString
    MAX-ACCESS read-only
    STATUS current
    DESCRIPTION "Name (CAPsMAN remote CAP)."
    ::= { mtxrWlCMRemoteEntry 2 }

mtxrWlCMRemoteState OBJECT-TYPE
    SYNTAX DisplayString
    MAX-ACCESS read-only
    STATUS current
    DESCRIPTION "State (CAPsMAN remote CAP)."
    ::= { mtxrWlCMRemoteEntry 3 }

mtxrWlCMRemoteAddress OBJECT-TYPE
    SYNTAX DisplayString
    MAX-ACCESS read-only
    STATUS current
    DESCRIPTION "Address (CAPsMAN remote CAP)."
    ::= { mtxrWlCMRemoteEntry 4 }

mtxrWlCMRemoteRadios OBJECT-TYPE
    SYNTAX Counter32
    MAX-ACCESS read-only
    STATUS current
    DESCRIPTION "Radios (CAPsMAN remote CAP)."
    ::= { mtxrWlCMRemoteEntry 5 }

-- W60G
mtxrWl60GTable OBJECT-TYPE
    SYNTAX SEQUENCE OF MtxrWl60GEntry
    MAX-ACCESS not-accessible
    STATUS current
    DESCRIPTION "Table of 60 GHz interface entries."
    ::= { mtxrWireless 8 }

mtxrWl60GEntry OBJECT-TYPE
    SYNTAX MtxrWl60GEntry
    MAX-ACCESS not-accessible
    STATUS current
    DESCRIPTION "W60G interface."
    INDEX { mtxrWl60GIndex }
    ::= { mtxrWl60GTable 1 }

MtxrWl60GEntry ::= SEQUENCE {
    mtxrWl60GIndex ObjectIndex,
    mtxrWl60GMode INTEGER,
    mtxrWl60GSsid DisplayString,
    mtxrWl60GConnected BoolValue,
    mtxrWl60GRemote MacAddress,
    mtxrWl60GFreq Integer32,
    mtxrWl60GMcs Integer32,
    mtxrWl60GSignal Integer32,
    mtxrWl60GTxSector Integer32,
    mtxrWl60GTxSectorInfo DisplayString,
    mtxrWl60GRssi Integer32,
    mtxrWl60GPhyRate Gauge32
}

mtxrWl60GIndex OBJECT-TYPE
    SYNTAX ObjectIndex
    MAX-ACCESS not-accessible
    STATUS current
    DESCRIPTION
        "Index identifying the row (internal object ID, not the console
         item number)."
    ::= { mtxrWl60GEntry 1 }

mtxrWl60GMode OBJECT-TYPE
    SYNTAX INTEGER {
        apBridge(0),
        stationBridge(1),
        sniff(2),
        bridge(3)
    }
    MAX-ACCESS read-only
    STATUS current
    DESCRIPTION "Mode (60 GHz interface)."
    ::= { mtxrWl60GEntry 2 }

mtxrWl60GSsid OBJECT-TYPE
    SYNTAX DisplayString
    MAX-ACCESS read-only
    STATUS current
    DESCRIPTION "SSID (60 GHz interface)."
    ::= { mtxrWl60GEntry 3 }

mtxrWl60GConnected OBJECT-TYPE
    SYNTAX BoolValue
    MAX-ACCESS read-only
    STATUS current
    DESCRIPTION "Connected (60 GHz interface)."
    ::= { mtxrWl60GEntry 4 }

mtxrWl60GRemote OBJECT-TYPE
    SYNTAX MacAddress
    MAX-ACCESS read-only
    STATUS current
    DESCRIPTION "Remote (60 GHz interface)."
    ::= { mtxrWl60GEntry 5 }

mtxrWl60GFreq OBJECT-TYPE
    SYNTAX Integer32
    UNITS "MHz"
    MAX-ACCESS read-only
    STATUS current
    DESCRIPTION "Frequency (60 GHz interface)."
    ::= { mtxrWl60GEntry 6 }

mtxrWl60GMcs OBJECT-TYPE
    SYNTAX Integer32
    MAX-ACCESS read-only
    STATUS current
    DESCRIPTION "MCS (60 GHz interface)."
    ::= { mtxrWl60GEntry 7 }

mtxrWl60GSignal OBJECT-TYPE
    SYNTAX Integer32
    MAX-ACCESS read-only
    STATUS current
    DESCRIPTION "Signal (60 GHz interface)."
    ::= { mtxrWl60GEntry 8 }

mtxrWl60GTxSector OBJECT-TYPE
    SYNTAX Integer32
    MAX-ACCESS read-only
    STATUS current
    DESCRIPTION "Transmit sector (60 GHz interface)."
    ::= { mtxrWl60GEntry 9 }

mtxrWl60GTxSectorInfo OBJECT-TYPE
    SYNTAX DisplayString
    MAX-ACCESS read-only
    STATUS current
    DESCRIPTION "Transmit sector info (60 GHz interface)."
    ::= { mtxrWl60GEntry 11 }

mtxrWl60GRssi OBJECT-TYPE
    SYNTAX Integer32
    MAX-ACCESS read-only
    STATUS current
    DESCRIPTION "RSSI (60 GHz interface)."
    ::= { mtxrWl60GEntry 12 }

mtxrWl60GPhyRate OBJECT-TYPE
    SYNTAX Gauge32
    UNITS "Mbit/s"
    MAX-ACCESS read-only
    STATUS current
    DESCRIPTION "PHY rate of the link."
    ::= { mtxrWl60GEntry 13 }

-- W60GSta
mtxrWl60GStaTable OBJECT-TYPE
    SYNTAX SEQUENCE OF MtxrWl60GStaEntry
    MAX-ACCESS not-accessible
    STATUS current
    DESCRIPTION "Table of 60 GHz station entries."
    ::= { mtxrWireless 9 }

mtxrWl60GStaEntry OBJECT-TYPE
    SYNTAX MtxrWl60GStaEntry
    MAX-ACCESS not-accessible
    STATUS current
    DESCRIPTION "W60G stations."
    INDEX { mtxrWl60GStaIndex }
    ::= { mtxrWl60GStaTable 1 }

MtxrWl60GStaEntry ::= SEQUENCE {
    mtxrWl60GStaIndex ObjectIndex,
    mtxrWl60GStaConnected BoolValue,
    mtxrWl60GStaRemote MacAddress,
    mtxrWl60GStaMcs Integer32,
    mtxrWl60GStaSignal Integer32,
    mtxrWl60GStaTxSector Integer32,
    mtxrWl60GStaPhyRate Gauge32,
    mtxrWl60GStaRssi Integer32,
    mtxrWl60GStaDistance Integer32
}

mtxrWl60GStaIndex OBJECT-TYPE
    SYNTAX ObjectIndex
    MAX-ACCESS not-accessible
    STATUS current
    DESCRIPTION
        "Index identifying the row (internal object ID, not the console
         item number)."
    ::= { mtxrWl60GStaEntry 1 }

mtxrWl60GStaConnected OBJECT-TYPE
    SYNTAX BoolValue
    MAX-ACCESS read-only
    STATUS current
    DESCRIPTION "Connected (60 GHz station)."
    ::= { mtxrWl60GStaEntry 2 }

mtxrWl60GStaRemote OBJECT-TYPE
    SYNTAX MacAddress
    MAX-ACCESS read-only
    STATUS current
    DESCRIPTION "Remote (60 GHz station)."
    ::= { mtxrWl60GStaEntry 3 }

mtxrWl60GStaMcs OBJECT-TYPE
    SYNTAX Integer32
    MAX-ACCESS read-only
    STATUS current
    DESCRIPTION "MCS (60 GHz station)."
    ::= { mtxrWl60GStaEntry 4 }

mtxrWl60GStaSignal OBJECT-TYPE
    SYNTAX Integer32
    MAX-ACCESS read-only
    STATUS current
    DESCRIPTION "Signal (60 GHz station)."
    ::= { mtxrWl60GStaEntry 5 }

mtxrWl60GStaTxSector OBJECT-TYPE
    SYNTAX Integer32
    MAX-ACCESS read-only
    STATUS current
    DESCRIPTION "Transmit sector (60 GHz station)."
    ::= { mtxrWl60GStaEntry 6 }

mtxrWl60GStaPhyRate OBJECT-TYPE
    SYNTAX Gauge32
    UNITS "Mbit/s"
    MAX-ACCESS read-only
    STATUS current
    DESCRIPTION "PHY rate of the station."
    ::= { mtxrWl60GStaEntry 8 }

mtxrWl60GStaRssi OBJECT-TYPE
    SYNTAX Integer32
    MAX-ACCESS read-only
    STATUS current
    DESCRIPTION "RSSI (60 GHz station)."
    ::= { mtxrWl60GStaEntry 9 }

mtxrWl60GStaDistance OBJECT-TYPE
    SYNTAX Integer32
    UNITS "m"
    MAX-ACCESS read-only
    STATUS current
    DESCRIPTION "Distance (60 GHz station)."
    ::= { mtxrWl60GStaEntry 10 }


mtxrWirelessGroup OBJECT-GROUP
    OBJECTS {
        mtxrWlStatTxRate,
        mtxrWlStatRxRate,
        mtxrWlStatStrength,
        mtxrWlStatSsid,
        mtxrWlStatBssid,
        mtxrWlStatFreq,
        mtxrWlStatBand,
        mtxrWlStatTxCCQ,
        mtxrWlStatRxCCQ,
        mtxrWlRtabStrength,
        mtxrWlRtabTxBytes,
        mtxrWlRtabRxBytes,
        mtxrWlRtabTxPackets,
        mtxrWlRtabRxPackets,
        mtxrWlRtabTxRate,
        mtxrWlRtabRxRate,
        mtxrWlRtabEntryCount,
        mtxrWlRtabRouterOSVersion,
        mtxrWlRtabUptime,
        mtxrWlRtabSignalToNoise,
        mtxrWlRtabTxStrengthCh0,
        mtxrWlRtabRxStrengthCh0,
        mtxrWlRtabTxStrengthCh1,
        mtxrWlRtabRxStrengthCh1,
        mtxrWlRtabTxStrengthCh2,
        mtxrWlRtabRxStrengthCh2,
        mtxrWlRtabTxStrength,
        mtxrWlRtabRadioName,
        mtxrWlApTxRate,
        mtxrWlApRxRate,
        mtxrWlApSsid,
        mtxrWlApBssid,
        mtxrWlApClientCount,
        mtxrWlApBand,
        mtxrWlApFreq,
        mtxrWlApNoiseFloor,
        mtxrWlApOverallTxCCQ,
        mtxrWlApAuthClientCount,
        mtxrWlCMRtabAddr,
        mtxrWlCMRtabTxBytes,
        mtxrWlCMRtabRxBytes,
        mtxrWlCMRtabTxPackets,
        mtxrWlCMRtabRxPackets,
        mtxrWlCMRtabTxRate,
        mtxrWlCMRtabRxRate,
        mtxrWlCMRtabUptime,
        mtxrWlCMRtabTxStrength,
        mtxrWlCMRtabRxStrength,
        mtxrWlCMRtabSsid,
        mtxrWlCMRtabEntryCount,
        mtxrWlCMREntryCount,
        mtxrWlCMRegClientCount,
        mtxrWlCMAuthClientCount,
        mtxrWl60GMode,
        mtxrWl60GSsid,
        mtxrWl60GConnected,
        mtxrWl60GRemote,
        mtxrWl60GFreq,
        mtxrWl60GMcs,
        mtxrWl60GSignal,
        mtxrWl60GTxSector,
        mtxrWl60GTxSectorInfo,
        mtxrWl60GRssi,
        mtxrWl60GPhyRate,
        mtxrWl60GStaConnected,
        mtxrWl60GStaRemote,
        mtxrWl60GStaMcs,
        mtxrWl60GStaSignal,
        mtxrWl60GStaTxSector,
        mtxrWl60GStaPhyRate,
        mtxrWl60GStaRssi,
        mtxrWl60GStaDistance,
        mtxrWlCMRtabEapIdent
    }
    STATUS current
    DESCRIPTION
        "Wireless interfaces, registration tables, CAPsMAN and 60 GHz
         links."
    ::= { mtXRouterOsGroups 1 }

-- QUEUES ********************************************************************

mtxrQueueSimpleTable OBJECT-TYPE
    SYNTAX SEQUENCE OF MtxrQueueSimpleEntry
    MAX-ACCESS not-accessible
    STATUS current
    DESCRIPTION "Table of simple queue entries."
    ::= { mtxrQueues 1 }

mtxrQueueSimpleEntry OBJECT-TYPE
    SYNTAX MtxrQueueSimpleEntry
    MAX-ACCESS not-accessible
    STATUS current
    DESCRIPTION "Simple queue."
    INDEX { mtxrQueueSimpleIndex }
    ::= { mtxrQueueSimpleTable 1 }

MtxrQueueSimpleEntry ::= SEQUENCE {
    mtxrQueueSimpleIndex ObjectIndex,
    mtxrQueueSimpleName DisplayString,
    mtxrQueueSimpleSrcAddr IpAddress,
    mtxrQueueSimpleSrcMask IpAddress,
    mtxrQueueSimpleDstAddr IpAddress,
    mtxrQueueSimpleDstMask IpAddress,
    mtxrQueueSimpleIface ObjectIndex,
    mtxrQueueSimpleBytesIn Counter64,
    mtxrQueueSimpleBytesOut Counter64,
    mtxrQueueSimplePacketsIn Counter32,
    mtxrQueueSimplePacketsOut Counter32,
    mtxrQueueSimplePCQQueuesIn Counter32,
    mtxrQueueSimplePCQQueuesOut Counter32,
    mtxrQueueSimpleDroppedIn Counter32,
    mtxrQueueSimpleDroppedOut Counter32
}

mtxrQueueSimpleIndex OBJECT-TYPE
    SYNTAX ObjectIndex
    MAX-ACCESS not-accessible
    STATUS current
    DESCRIPTION
        "Index identifying the row (internal object ID, not the console
         item number)."
    ::= { mtxrQueueSimpleEntry 1 }

mtxrQueueSimpleName OBJECT-TYPE
    SYNTAX DisplayString
    MAX-ACCESS read-only
    STATUS current
    DESCRIPTION "Name (simple queue)."
    ::= { mtxrQueueSimpleEntry 2 }

mtxrQueueSimpleSrcAddr OBJECT-TYPE
    SYNTAX IpAddress
    MAX-ACCESS read-only
    STATUS current
    DESCRIPTION "Src address (simple queue)."
    ::= { mtxrQueueSimpleEntry 3 }

mtxrQueueSimpleSrcMask OBJECT-TYPE
    SYNTAX IpAddress
    MAX-ACCESS read-only
    STATUS current
    DESCRIPTION "Src mask (simple queue)."
    ::= { mtxrQueueSimpleEntry 4 }

mtxrQueueSimpleDstAddr OBJECT-TYPE
    SYNTAX IpAddress
    MAX-ACCESS read-only
    STATUS current
    DESCRIPTION "Dst address (simple queue)."
    ::= { mtxrQueueSimpleEntry 5 }

mtxrQueueSimpleDstMask OBJECT-TYPE
    SYNTAX IpAddress
    MAX-ACCESS read-only
    STATUS current
    DESCRIPTION "Dst mask (simple queue)."
    ::= { mtxrQueueSimpleEntry 6 }

mtxrQueueSimpleIface OBJECT-TYPE
    SYNTAX ObjectIndex
    MAX-ACCESS read-only
    STATUS current
    DESCRIPTION "Interface index."
    ::= { mtxrQueueSimpleEntry 7 }

mtxrQueueSimpleBytesIn OBJECT-TYPE
    SYNTAX Counter64
    UNITS "bytes"
    MAX-ACCESS read-only
    STATUS current
    DESCRIPTION "Bytes in (simple queue)."
    ::= { mtxrQueueSimpleEntry 8 }

mtxrQueueSimpleBytesOut OBJECT-TYPE
    SYNTAX Counter64
    UNITS "bytes"
    MAX-ACCESS read-only
    STATUS current
    DESCRIPTION "Bytes out (simple queue)."
    ::= { mtxrQueueSimpleEntry 9 }

mtxrQueueSimplePacketsIn OBJECT-TYPE
    SYNTAX Counter32
    UNITS "packets"
    MAX-ACCESS read-only
    STATUS current
    DESCRIPTION "Packets in (simple queue)."
    ::= { mtxrQueueSimpleEntry 10 }

mtxrQueueSimplePacketsOut OBJECT-TYPE
    SYNTAX Counter32
    UNITS "packets"
    MAX-ACCESS read-only
    STATUS current
    DESCRIPTION "Packets out (simple queue)."
    ::= { mtxrQueueSimpleEntry 11 }

mtxrQueueSimplePCQQueuesIn OBJECT-TYPE
    SYNTAX Counter32
    MAX-ACCESS read-only
    STATUS current
    DESCRIPTION "PCQ queues in (simple queue)."
    ::= { mtxrQueueSimpleEntry 12 }

mtxrQueueSimplePCQQueuesOut OBJECT-TYPE
    SYNTAX Counter32
    MAX-ACCESS read-only
    STATUS current
    DESCRIPTION "PCQ queues out (simple queue)."
    ::= { mtxrQueueSimpleEntry 13 }

mtxrQueueSimpleDroppedIn OBJECT-TYPE
    SYNTAX Counter32
    MAX-ACCESS read-only
    STATUS current
    DESCRIPTION "Dropped in (simple queue)."
    ::= { mtxrQueueSimpleEntry 14 }

mtxrQueueSimpleDroppedOut OBJECT-TYPE
    SYNTAX Counter32
    MAX-ACCESS read-only
    STATUS current
    DESCRIPTION "Dropped out (simple queue)."
    ::= { mtxrQueueSimpleEntry 15 }

mtxrQueueTreeTable OBJECT-TYPE
    SYNTAX SEQUENCE OF MtxrQueueTreeEntry
    MAX-ACCESS not-accessible
    STATUS current
    DESCRIPTION "Table of queue tree entries."
    ::= { mtxrQueues 2 }

mtxrQueueTreeEntry OBJECT-TYPE
    SYNTAX MtxrQueueTreeEntry
    MAX-ACCESS not-accessible
    STATUS current
    DESCRIPTION "Tree queue."
    INDEX { mtxrQueueTreeIndex }
    ::= { mtxrQueueTreeTable 1 }

MtxrQueueTreeEntry ::= SEQUENCE {
    mtxrQueueTreeIndex ObjectIndex,
    mtxrQueueTreeName DisplayString,
    mtxrQueueTreeFlow DisplayString,
    mtxrQueueTreeParentIndex ObjectIndex,
    mtxrQueueTreeBytes Counter32,
    mtxrQueueTreePackets Counter32,
    mtxrQueueTreeHCBytes Counter64,
    mtxrQueueTreePCQQueues Counter32,
    mtxrQueueTreeDropped Counter32
}

mtxrQueueTreeIndex OBJECT-TYPE
    SYNTAX ObjectIndex
    MAX-ACCESS not-accessible
    STATUS current
    DESCRIPTION
        "Index identifying the row (internal object ID, not the console
         item number)."
    ::= { mtxrQueueTreeEntry 1 }

mtxrQueueTreeName OBJECT-TYPE
    SYNTAX DisplayString
    MAX-ACCESS read-only
    STATUS current
    DESCRIPTION "Name (queue tree)."
    ::= { mtxrQueueTreeEntry 2 }

mtxrQueueTreeFlow OBJECT-TYPE
    SYNTAX DisplayString
    MAX-ACCESS read-only
    STATUS current
    DESCRIPTION "Flowmark."
    ::= { mtxrQueueTreeEntry 3 }

mtxrQueueTreeParentIndex OBJECT-TYPE
    SYNTAX ObjectIndex
    MAX-ACCESS read-only
    STATUS current
    DESCRIPTION "Index of parent tree queue or parent interface."
    ::= { mtxrQueueTreeEntry 4 }

mtxrQueueTreeBytes OBJECT-TYPE
    SYNTAX Counter32
    UNITS "bytes"
    MAX-ACCESS read-only
    STATUS current
    DESCRIPTION "Bytes (queue tree)."
    ::= { mtxrQueueTreeEntry 5 }

mtxrQueueTreePackets OBJECT-TYPE
    SYNTAX Counter32
    UNITS "packets"
    MAX-ACCESS read-only
    STATUS current
    DESCRIPTION "Packets (queue tree)."
    ::= { mtxrQueueTreeEntry 6 }

mtxrQueueTreeHCBytes OBJECT-TYPE
    SYNTAX Counter64
    UNITS "bytes"
    MAX-ACCESS read-only
    STATUS current
    DESCRIPTION "64-bit bytes (queue tree)."
    ::= { mtxrQueueTreeEntry 7 }

mtxrQueueTreePCQQueues OBJECT-TYPE
    SYNTAX Counter32
    MAX-ACCESS read-only
    STATUS current
    DESCRIPTION "PCQ queues (queue tree)."
    ::= { mtxrQueueTreeEntry 8 }

mtxrQueueTreeDropped OBJECT-TYPE
    SYNTAX Counter32
    MAX-ACCESS read-only
    STATUS current
    DESCRIPTION "Dropped (queue tree)."
    ::= { mtxrQueueTreeEntry 9 }

mtxrQueueGroup OBJECT-GROUP
    OBJECTS {
        mtxrQueueSimpleName,
        mtxrQueueSimpleSrcAddr,
        mtxrQueueSimpleSrcMask,
        mtxrQueueSimpleDstAddr,
        mtxrQueueSimpleDstMask,
        mtxrQueueSimpleIface,
        mtxrQueueSimpleBytesIn,
        mtxrQueueSimpleBytesOut,
        mtxrQueueSimplePacketsIn,
        mtxrQueueSimplePacketsOut,
        mtxrQueueTreeName,
        mtxrQueueSimplePCQQueuesIn,
        mtxrQueueSimplePCQQueuesOut,
        mtxrQueueSimpleDroppedIn,
        mtxrQueueSimpleDroppedOut,
        mtxrQueueTreeFlow,
        mtxrQueueTreeParentIndex,
        mtxrQueueTreeBytes,
        mtxrQueueTreePackets,
        mtxrQueueTreeHCBytes,
        mtxrQueueTreePCQQueues,
        mtxrQueueTreeDropped
    }
    STATUS current
    DESCRIPTION "Simple queues and queue tree statistics."
    ::= { mtXRouterOsGroups 2 }

-- HEALTH ********************************************************************

mtxrHlCoreVoltage OBJECT-TYPE
    SYNTAX Voltage
    UNITS "V"
    MAX-ACCESS read-only
    STATUS current
    DESCRIPTION "Core voltage."
    ::= { mtxrHealth 1 }

mtxrHlThreeDotThreeVoltage OBJECT-TYPE
    SYNTAX Voltage
    UNITS "V"
    MAX-ACCESS read-only
    STATUS current
    DESCRIPTION "3.3V voltage."
    ::= { mtxrHealth 2 }

mtxrHlFiveVoltage OBJECT-TYPE
    SYNTAX Voltage
    UNITS "V"
    MAX-ACCESS read-only
    STATUS current
    DESCRIPTION "5V voltage."
    ::= { mtxrHealth 3 }

mtxrHlTwelveVoltage OBJECT-TYPE
    SYNTAX Voltage
    UNITS "V"
    MAX-ACCESS read-only
    STATUS current
    DESCRIPTION "12V voltage."
    ::= { mtxrHealth 4 }

mtxrHlSensorTemperature OBJECT-TYPE
    SYNTAX Temperature
    UNITS "degrees Celsius"
    MAX-ACCESS read-only
    STATUS current
    DESCRIPTION "Temperature at sensor chip."
    ::= { mtxrHealth 5 }

mtxrHlCpuTemperature OBJECT-TYPE
    SYNTAX Temperature
    UNITS "degrees Celsius"
    MAX-ACCESS read-only
    STATUS current
    DESCRIPTION "Temperature near cpu."
    ::= { mtxrHealth 6 }

mtxrHlBoardTemperature OBJECT-TYPE
    SYNTAX Temperature
    UNITS "degrees Celsius"
    MAX-ACCESS read-only
    STATUS current
    DESCRIPTION "Board temperature (system health)."
    ::= { mtxrHealth 7 }

mtxrHlVoltage OBJECT-TYPE
    SYNTAX Voltage
    UNITS "V"
    MAX-ACCESS read-only
    STATUS current
    DESCRIPTION "Voltage (system health)."
    ::= { mtxrHealth 8 }

mtxrHlActiveFan OBJECT-TYPE
    SYNTAX DisplayString
    MAX-ACCESS read-only
    STATUS current
    DESCRIPTION "Name of the currently active fan (or fan profile)."
    ::= { mtxrHealth 9 }

mtxrHlTemperature OBJECT-TYPE
    SYNTAX Temperature
    UNITS "degrees Celsius"
    MAX-ACCESS read-only
    STATUS current
    DESCRIPTION "Temperature (system health)."
    ::= { mtxrHealth 10 }

mtxrHlProcessorTemperature OBJECT-TYPE
    SYNTAX Temperature
    UNITS "degrees Celsius"
    MAX-ACCESS read-only
    STATUS current
    DESCRIPTION "Processor temperature (system health)."
    ::= { mtxrHealth 11 }

mtxrHlPower OBJECT-TYPE
    SYNTAX Power
    UNITS "W"
    MAX-ACCESS read-only
    STATUS current
    DESCRIPTION "Power (system health)."
    ::= { mtxrHealth 12 }

mtxrHlCurrent OBJECT-TYPE
    SYNTAX Integer32
    UNITS "mA"
    MAX-ACCESS read-only
    STATUS current
    DESCRIPTION "Current (system health)."
    ::= { mtxrHealth 13 }

mtxrHlProcessorFrequency OBJECT-TYPE
    SYNTAX Integer32
    UNITS "MHz"
    MAX-ACCESS read-only
    STATUS current
    DESCRIPTION "Processor frequency (system health)."
    ::= { mtxrHealth 14 }

mtxrHlPowerSupplyState OBJECT-TYPE
    SYNTAX BoolValue
    MAX-ACCESS read-only
    STATUS current
    DESCRIPTION "PSU state ok."
    ::= { mtxrHealth 15 }

mtxrHlBackupPowerSupplyState OBJECT-TYPE
    SYNTAX BoolValue
    MAX-ACCESS read-only
    STATUS current
    DESCRIPTION "Backup PSU state ok."
    ::= { mtxrHealth 16 }

mtxrHlFanSpeed1 OBJECT-TYPE
    SYNTAX Gauge32
    UNITS "rpm"
    MAX-ACCESS read-only
    STATUS current
    DESCRIPTION "Fan speed1 (system health)."
    ::= { mtxrHealth 17 }

mtxrHlFanSpeed2 OBJECT-TYPE
    SYNTAX Gauge32
    UNITS "rpm"
    MAX-ACCESS read-only
    STATUS current
    DESCRIPTION "Fan speed2 (system health)."
    ::= { mtxrHealth 18 }

mtxrAlarmSocketStatus OBJECT-TYPE
    SYNTAX INTEGER {
        inactive(0),
        active(1)
    }
    MAX-ACCESS read-only
    STATUS current
    DESCRIPTION "Alarm socket status."
    ::= { mtxrHealth 19 }

mtxrGaugeTable OBJECT-TYPE
    SYNTAX SEQUENCE OF MtxrGaugeTableEntry
    MAX-ACCESS not-accessible
    STATUS current
    DESCRIPTION "Table of health gauge entries."
    ::= { mtxrHealth 100 }

mtxrGaugeTableEntry OBJECT-TYPE
    SYNTAX MtxrGaugeTableEntry
    MAX-ACCESS not-accessible
    STATUS current
    DESCRIPTION "Entry of the health gauge table."
    INDEX { mtxrGaugeIndex }
    ::= { mtxrGaugeTable 1 }

MtxrGaugeTableEntry ::= SEQUENCE {
    mtxrGaugeIndex ObjectIndex,
    mtxrGaugeName DisplayString,
    mtxrGaugeValue Integer32,
    mtxrGaugeUnit INTEGER
}

mtxrGaugeIndex OBJECT-TYPE
    SYNTAX ObjectIndex
    MAX-ACCESS not-accessible
    STATUS current
    DESCRIPTION
        "Index identifying the row (internal object ID, not the console
         item number)."
    ::= { mtxrGaugeTableEntry 1 }

mtxrGaugeName OBJECT-TYPE
    SYNTAX DisplayString
    MAX-ACCESS read-only
    STATUS current
    DESCRIPTION "Name (health gauge)."
    ::= { mtxrGaugeTableEntry 2 }

mtxrGaugeValue OBJECT-TYPE
    SYNTAX Integer32
    MAX-ACCESS read-only
    STATUS current
    DESCRIPTION
        "Gauge value. The unit is given by mtxrGaugeUnit; dV, dA and dW are
         tenths of volt, ampere and watt."
    ::= { mtxrGaugeTableEntry 3 }

mtxrGaugeUnit OBJECT-TYPE
    SYNTAX INTEGER {
        celsius(1),
        rpm(2),
        dV(3),
        dA(4),
        dW(5),
        status(6)
    }
    MAX-ACCESS read-only
    STATUS current
    DESCRIPTION
        "Unit of mtxrGaugeValue (dV = 0.1 V, dA = 0.1 A, dW = 0.1 W)."
    ::= { mtxrGaugeTableEntry 4 }

mtxrHealthGroup OBJECT-GROUP
    OBJECTS {
        mtxrHlCoreVoltage,
        mtxrHlThreeDotThreeVoltage,
        mtxrHlFiveVoltage,
        mtxrHlTwelveVoltage,
        mtxrHlSensorTemperature,
        mtxrHlCpuTemperature,
        mtxrHlBoardTemperature,
        mtxrHlVoltage,
        mtxrHlActiveFan,
        mtxrHlTemperature,
        mtxrHlProcessorTemperature,
        mtxrHlCurrent,
        mtxrHlPower,
        mtxrHlProcessorFrequency,
        mtxrHlPowerSupplyState,
        mtxrHlBackupPowerSupplyState,
        mtxrHlFanSpeed1,
        mtxrHlFanSpeed2,
        mtxrAlarmSocketStatus,
        mtxrGaugeName,
        mtxrGaugeValue,
        mtxrGaugeUnit
    }
    STATUS current
    DESCRIPTION
        "Voltages, temperatures, fans, power supplies and health gauges."
    ::= { mtXRouterOsGroups 3 }

-- LICENSE ********************************************************************

mtxrLicSoftwareId OBJECT-TYPE
    SYNTAX DisplayString
    MAX-ACCESS read-only
    STATUS current
    DESCRIPTION "Software id."
    ::= { mtxrLicense 1 }

mtxrLicUpgrUntil OBJECT-TYPE
    SYNTAX DateAndTime
    MAX-ACCESS read-only
    STATUS current
    DESCRIPTION "Current key allows upgrading until this date."
    ::= { mtxrLicense 2 }

mtxrLicLevel OBJECT-TYPE
    SYNTAX Integer32
    MAX-ACCESS read-only
    STATUS current
    DESCRIPTION "Current key level."
    ::= { mtxrLicense 3 }

mtxrLicVersion OBJECT-TYPE
    SYNTAX DisplayString
    MAX-ACCESS read-only
    STATUS current
    DESCRIPTION "Software version."
    ::= { mtxrLicense 4 }

mtxrLicUpgradableTo OBJECT-TYPE
    SYNTAX Integer32
    MAX-ACCESS read-only
    STATUS current
    DESCRIPTION "Upgradable to."
    ::= { mtxrLicense 5 }

mtxrLincenseGroup OBJECT-GROUP
    OBJECTS {
        mtxrLicSoftwareId,
        mtxrLicUpgrUntil,
        mtxrLicLevel,
        mtxrLicVersion,
        mtxrLicUpgradableTo
    }
    STATUS current
    DESCRIPTION "RouterOS license information."
    ::= { mtXRouterOsGroups 4 }

-- HOTSPOT ***************************************************************

mtxrHotspotActiveUsersTable OBJECT-TYPE
    SYNTAX SEQUENCE OF MtxrHotspotActiveUsersTableEntry
    MAX-ACCESS not-accessible
    STATUS current
    DESCRIPTION "Table of hotspot active user entries."
    ::= { mtxrHotspot 1 }

mtxrHotspotActiveUsersTableEntry OBJECT-TYPE
    SYNTAX MtxrHotspotActiveUsersTableEntry
    MAX-ACCESS not-accessible
    STATUS current
    DESCRIPTION "Entry of the hotspot active user table."
    INDEX { mtxrHotspotActiveUserIndex }
    ::= { mtxrHotspotActiveUsersTable 1 }

MtxrHotspotActiveUsersTableEntry ::= SEQUENCE {
        mtxrHotspotActiveUserIndex ObjectIndex,
        mtxrHotspotActiveUserServerID Integer32,
        mtxrHotspotActiveUserName DisplayString,
        mtxrHotspotActiveUserDomain DisplayString,
        mtxrHotspotActiveUserIP IpAddress,
        mtxrHotspotActiveUserMAC MacAddress,
        mtxrHotspotActiveUserConnectTime Integer32,
        mtxrHotspotActiveUserValidTillTime Integer32,
        mtxrHotspotActiveUserIdleStartTime Integer32,
        mtxrHotspotActiveUserIdleTimeout Integer32,
        mtxrHotspotActiveUserPingTimeout Integer32,
        mtxrHotspotActiveUserBytesIn Counter64,
        mtxrHotspotActiveUserBytesOut Counter64,
        mtxrHotspotActiveUserPacketsIn Counter64,
        mtxrHotspotActiveUserPacketsOut Counter64,
        mtxrHotspotActiveUserLimitBytesIn Counter64,
        mtxrHotspotActiveUserLimitBytesOut Counter64,
        mtxrHotspotActiveUserAdvertStatus Integer32,
        mtxrHotspotActiveUserRadius Integer32,
        mtxrHotspotActiveUserBlockedByAdvert Integer32
}

mtxrHotspotActiveUserIndex OBJECT-TYPE
    SYNTAX ObjectIndex
    MAX-ACCESS not-accessible
    STATUS current
    DESCRIPTION
        "Index identifying the row (internal object ID, not the console
         item number)."
    ::= { mtxrHotspotActiveUsersTableEntry 1 }

mtxrHotspotActiveUserServerID OBJECT-TYPE
    SYNTAX Integer32
    MAX-ACCESS read-only
    STATUS current
    DESCRIPTION "Server ID (hotspot active user)."
    ::= { mtxrHotspotActiveUsersTableEntry 2 }

mtxrHotspotActiveUserName OBJECT-TYPE
    SYNTAX DisplayString
    MAX-ACCESS read-only
    STATUS current
    DESCRIPTION "Name (hotspot active user)."
    ::= { mtxrHotspotActiveUsersTableEntry 3 }

mtxrHotspotActiveUserDomain OBJECT-TYPE
    SYNTAX DisplayString
    MAX-ACCESS read-only
    STATUS current
    DESCRIPTION "Domain (hotspot active user)."
    ::= { mtxrHotspotActiveUsersTableEntry 4 }

mtxrHotspotActiveUserIP OBJECT-TYPE
    SYNTAX IpAddress
    MAX-ACCESS read-only
    STATUS current
    DESCRIPTION "IP (hotspot active user)."
    ::= { mtxrHotspotActiveUsersTableEntry 5 }

mtxrHotspotActiveUserMAC OBJECT-TYPE
    SYNTAX MacAddress
    MAX-ACCESS read-only
    STATUS current
    DESCRIPTION "MAC (hotspot active user)."
    ::= { mtxrHotspotActiveUsersTableEntry 6 }

mtxrHotspotActiveUserConnectTime OBJECT-TYPE
    SYNTAX Integer32
    MAX-ACCESS read-only
    STATUS current
    DESCRIPTION "Connect time (hotspot active user)."
    ::= { mtxrHotspotActiveUsersTableEntry 7 }

mtxrHotspotActiveUserValidTillTime OBJECT-TYPE
    SYNTAX Integer32
    MAX-ACCESS read-only
    STATUS current
    DESCRIPTION "Valid till time (hotspot active user)."
    ::= { mtxrHotspotActiveUsersTableEntry 8 }

mtxrHotspotActiveUserIdleStartTime OBJECT-TYPE
    SYNTAX Integer32
    MAX-ACCESS read-only
    STATUS current
    DESCRIPTION "Idle start time (hotspot active user)."
    ::= { mtxrHotspotActiveUsersTableEntry 9 }

mtxrHotspotActiveUserIdleTimeout OBJECT-TYPE
    SYNTAX Integer32
    MAX-ACCESS read-only
    STATUS current
    DESCRIPTION "Idle timeout (hotspot active user)."
    ::= { mtxrHotspotActiveUsersTableEntry 10 }

mtxrHotspotActiveUserPingTimeout OBJECT-TYPE
    SYNTAX Integer32
    MAX-ACCESS read-only
    STATUS current
    DESCRIPTION "Ping timeout (hotspot active user)."
    ::= { mtxrHotspotActiveUsersTableEntry 11 }

mtxrHotspotActiveUserBytesIn OBJECT-TYPE
    SYNTAX Counter64
    UNITS "bytes"
    MAX-ACCESS read-only
    STATUS current
    DESCRIPTION "Bytes in (hotspot active user)."
    ::= { mtxrHotspotActiveUsersTableEntry 12 }

mtxrHotspotActiveUserBytesOut OBJECT-TYPE
    SYNTAX Counter64
    UNITS "bytes"
    MAX-ACCESS read-only
    STATUS current
    DESCRIPTION "Bytes out (hotspot active user)."
    ::= { mtxrHotspotActiveUsersTableEntry 13 }

mtxrHotspotActiveUserPacketsIn OBJECT-TYPE
    SYNTAX Counter64
    UNITS "packets"
    MAX-ACCESS read-only
    STATUS current
    DESCRIPTION "Packets in (hotspot active user)."
    ::= { mtxrHotspotActiveUsersTableEntry 14 }

mtxrHotspotActiveUserPacketsOut OBJECT-TYPE
    SYNTAX Counter64
    UNITS "packets"
    MAX-ACCESS read-only
    STATUS current
    DESCRIPTION "Packets out (hotspot active user)."
    ::= { mtxrHotspotActiveUsersTableEntry 15 }

mtxrHotspotActiveUserLimitBytesIn OBJECT-TYPE
    SYNTAX Counter64
    UNITS "bytes"
    MAX-ACCESS read-only
    STATUS current
    DESCRIPTION "Limit bytes in (hotspot active user)."
    ::= { mtxrHotspotActiveUsersTableEntry 16 }

mtxrHotspotActiveUserLimitBytesOut OBJECT-TYPE
    SYNTAX Counter64
    UNITS "bytes"
    MAX-ACCESS read-only
    STATUS current
    DESCRIPTION "Limit bytes out (hotspot active user)."
    ::= { mtxrHotspotActiveUsersTableEntry 17 }

mtxrHotspotActiveUserAdvertStatus OBJECT-TYPE
    SYNTAX Integer32
    MAX-ACCESS read-only
    STATUS current
    DESCRIPTION "Advert status (hotspot active user)."
    ::= { mtxrHotspotActiveUsersTableEntry 18 }

mtxrHotspotActiveUserRadius OBJECT-TYPE
    SYNTAX Integer32
    MAX-ACCESS read-only
    STATUS current
    DESCRIPTION "RADIUS (hotspot active user)."
    ::= { mtxrHotspotActiveUsersTableEntry 19 }

mtxrHotspotActiveUserBlockedByAdvert OBJECT-TYPE
    SYNTAX Integer32
    MAX-ACCESS read-only
    STATUS current
    DESCRIPTION "Blocked by advert (hotspot active user)."
    ::= { mtxrHotspotActiveUsersTableEntry 20 }

mtxrHotspotActiveUserCount OBJECT-TYPE
    SYNTAX Gauge32
    MAX-ACCESS read-only
    STATUS current
    DESCRIPTION "Number of active (logged-in) HotSpot clients."
    ::= { mtxrHotspot 2 }

mtxrHotspotHostCount OBJECT-TYPE
    SYNTAX Gauge32
    MAX-ACCESS read-only
    STATUS current
    DESCRIPTION "Number of HotSpot hosts."
    ::= { mtxrHotspot 3 }

mtxrHotspotActiveUserGroup OBJECT-GROUP
    OBJECTS {
        mtxrHotspotActiveUserServerID,
        mtxrHotspotActiveUserName,
        mtxrHotspotActiveUserDomain,
        mtxrHotspotActiveUserIP,
        mtxrHotspotActiveUserMAC,
        mtxrHotspotActiveUserConnectTime,
        mtxrHotspotActiveUserValidTillTime,
        mtxrHotspotActiveUserIdleStartTime,
        mtxrHotspotActiveUserIdleTimeout,
        mtxrHotspotActiveUserPingTimeout,
        mtxrHotspotActiveUserBytesIn,
        mtxrHotspotActiveUserBytesOut,
        mtxrHotspotActiveUserPacketsIn,
        mtxrHotspotActiveUserPacketsOut,
        mtxrHotspotActiveUserLimitBytesIn,
        mtxrHotspotActiveUserLimitBytesOut,
        mtxrHotspotActiveUserAdvertStatus,
        mtxrHotspotActiveUserRadius,
        mtxrHotspotActiveUserBlockedByAdvert
    }
    STATUS current
    DESCRIPTION "Hotspot active user table."
    ::= { mtXRouterOsGroups 5 }

mtxrHotspotCountGroup OBJECT-GROUP
    OBJECTS {
        mtxrHotspotActiveUserCount,
        mtxrHotspotHostCount
    }
    STATUS current
    DESCRIPTION "Hotspot user and host counters."
    ::= { mtXRouterOsGroups 26 }

-- DHCP ********************************************************************

mtxrDHCPLeaseCount OBJECT-TYPE
    SYNTAX Gauge32
    MAX-ACCESS read-only
    STATUS current
    DESCRIPTION "Lease count (DHCP server)."
    ::= { mtxrDHCP 1 }

mtxrDHCPGroup OBJECT-GROUP
    OBJECTS {
        mtxrDHCPLeaseCount
    }
    STATUS current
    DESCRIPTION "DHCP server counters."
    ::= { mtXRouterOsGroups 12 }

-- SYSTEM ********************************************************************

mtxrSystemReboot OBJECT-TYPE
    SYNTAX Integer32
    MAX-ACCESS read-write
    STATUS current
    DESCRIPTION "Write a non-zero value to reboot the router."
    ::= { mtxrSystem 1 }

mtxrUSBPowerReset OBJECT-TYPE
    SYNTAX Integer32
    UNITS "seconds"
    MAX-ACCESS read-write
    STATUS current
    DESCRIPTION
        "Switches the USB power off for the given number of seconds."
    ::= { mtxrSystem 2 }

mtxrSerialNumber OBJECT-TYPE
    SYNTAX DisplayString
    MAX-ACCESS read-only
    STATUS current
    DESCRIPTION "RouterBOARD serial number."
    ::= { mtxrSystem 3 }

mtxrFirmwareVersion OBJECT-TYPE
    SYNTAX DisplayString
    MAX-ACCESS read-only
    STATUS current
    DESCRIPTION "Current firmware version."
    ::= { mtxrSystem 4 }

mtxrNote OBJECT-TYPE
    SYNTAX DisplayString
    MAX-ACCESS read-only
    STATUS current
    DESCRIPTION "Note."
    ::= { mtxrSystem 5 }

mtxrBuildTime OBJECT-TYPE
    SYNTAX DisplayString
    MAX-ACCESS read-only
    STATUS current
    DESCRIPTION "Build time."
    ::= { mtxrSystem 6 }

mtxrFirmwareUpgradeVersion OBJECT-TYPE
    SYNTAX DisplayString
    MAX-ACCESS read-only
    STATUS current
    DESCRIPTION "Upgrade firmware version."
    ::= { mtxrSystem 7 }

mtxrDisplayName OBJECT-TYPE
    SYNTAX DisplayString
    MAX-ACCESS read-only
    STATUS current
    DESCRIPTION "Display name."
    ::= { mtxrSystem 8 }

mtxrBoardName OBJECT-TYPE
    SYNTAX DisplayString
    MAX-ACCESS read-only
    STATUS current
    DESCRIPTION "Board name."
    ::= { mtxrSystem 9 }

mtxrSystemGroup OBJECT-GROUP
    OBJECTS {
        mtxrSystemReboot,
        mtxrUSBPowerReset,
        mtxrSerialNumber,
        mtxrFirmwareVersion,
        mtxrNote,
        mtxrBuildTime,
        mtxrFirmwareUpgradeVersion,
        mtxrDisplayName,
        mtxrBoardName
    }
    STATUS current
    DESCRIPTION "System information and control (reboot, USB power)."
    ::= { mtXRouterOsGroups 13 }

-- SCRIPTS ********************************************************************

mtxrScriptTable OBJECT-TYPE
    SYNTAX SEQUENCE OF MtxrScriptTableEntry
    MAX-ACCESS not-accessible
    STATUS current
    DESCRIPTION "Table of script entries."
    ::= { mtxrScripts 1 }

mtxrScriptTableEntry OBJECT-TYPE
    SYNTAX MtxrScriptTableEntry
    MAX-ACCESS not-accessible
    STATUS current
    DESCRIPTION "Entry of the script table."
    INDEX { mtxrScriptIndex }
    ::= { mtxrScriptTable 1 }

MtxrScriptTableEntry ::= SEQUENCE {
        mtxrScriptIndex ObjectIndex,
        mtxrScriptName DisplayString,
        mtxrScriptRunCmd Integer32
}

mtxrScriptIndex OBJECT-TYPE
    SYNTAX ObjectIndex
    MAX-ACCESS not-accessible
    STATUS current
    DESCRIPTION
        "Index identifying the row (internal object ID, not the console
         item number)."
    ::= { mtxrScriptTableEntry 1 }

mtxrScriptName OBJECT-TYPE
    SYNTAX DisplayString
    MAX-ACCESS read-only
    STATUS current
    DESCRIPTION "Name (script)."
    ::= { mtxrScriptTableEntry 2 }

mtxrScriptRunCmd OBJECT-TYPE
    SYNTAX Integer32
    MAX-ACCESS read-write
    STATUS current
    DESCRIPTION "Write a non-zero value to run this script."
    ::= { mtxrScriptTableEntry 3 }

mtxrScriptGroup OBJECT-GROUP
    OBJECTS {
        mtxrScriptName,
        mtxrScriptRunCmd
    }
    STATUS current
    DESCRIPTION "Scripts that can be started over SNMP."
    ::= { mtXRouterOsGroups 8 }

-- SCRIPT RUN *****************************************************************

mtxrScriptRunTable OBJECT-TYPE
    SYNTAX SEQUENCE OF MtxrScriptRunTableEntry
    MAX-ACCESS not-accessible
    STATUS current
    DESCRIPTION
        "Invisible to getnext, accesible only with get request and write
         premission."
    ::= { mtxrScriptRun 1 }

mtxrScriptRunTableEntry OBJECT-TYPE
    SYNTAX MtxrScriptRunTableEntry
    MAX-ACCESS not-accessible
    STATUS current
    DESCRIPTION "Entry of the script execution table."
    INDEX { mtxrScriptRunIndex }
    ::= { mtxrScriptRunTable 1 }

MtxrScriptRunTableEntry ::= SEQUENCE {
        mtxrScriptRunIndex ObjectIndex,
        mtxrScriptRunOutput DisplayString
}

mtxrScriptRunIndex OBJECT-TYPE
    SYNTAX ObjectIndex
    MAX-ACCESS not-accessible
    STATUS current
    DESCRIPTION
        "Index identifying the row (internal object ID, not the console
         item number)."
    ::= { mtxrScriptRunTableEntry 1 }

mtxrScriptRunOutput OBJECT-TYPE
    SYNTAX DisplayString
    MAX-ACCESS read-only
    STATUS current
    DESCRIPTION
        "This oid on get request will run script and return it's output."
    ::= { mtxrScriptRunTableEntry 2 }

mtxrScriptRunGroup OBJECT-GROUP
    OBJECTS {
        mtxrScriptRunOutput
    }
    STATUS current
    DESCRIPTION "Script execution with output returned over SNMP."
    ::= { mtXRouterOsGroups 21 }

-- Dual Nstreme ***************************************************************

mtxrDnStatTable OBJECT-TYPE
    SYNTAX SEQUENCE OF MtxrDnStatEntry
    MAX-ACCESS not-accessible
    STATUS current
    DESCRIPTION "Table of Nstreme Dual interface entries."
    ::= { mtxrNstremeDual 1 }

mtxrDnStatEntry OBJECT-TYPE
    SYNTAX MtxrDnStatEntry
    MAX-ACCESS not-accessible
    STATUS current
    DESCRIPTION "Nstreme Dual interface."
    INDEX { mtxrDnStatIndex }
    ::= { mtxrDnStatTable 1 }

MtxrDnStatEntry ::= SEQUENCE {
    mtxrDnStatIndex ObjectIndex,
    mtxrDnStatTxRate Gauge32,
    mtxrDnStatRxRate Gauge32,
    mtxrDnStatTxStrength Integer32,
    mtxrDnStatRxStrength Integer32,
    mtxrDnConnected Integer32
}

mtxrDnStatIndex OBJECT-TYPE
    SYNTAX ObjectIndex
    MAX-ACCESS not-accessible
    STATUS current
    DESCRIPTION
        "Index identifying the row (internal object ID, not the console
         item number)."
    ::= { mtxrDnStatEntry 1 }

mtxrDnStatTxRate OBJECT-TYPE
    SYNTAX Gauge32
    UNITS "bits per second"
    MAX-ACCESS read-only
    STATUS current
    DESCRIPTION "Stat transmit rate (Nstreme Dual interface)."
    ::= { mtxrDnStatEntry 2 }

mtxrDnStatRxRate OBJECT-TYPE
    SYNTAX Gauge32
    UNITS "bits per second"
    MAX-ACCESS read-only
    STATUS current
    DESCRIPTION "Stat receive rate (Nstreme Dual interface)."
    ::= { mtxrDnStatEntry 3 }

mtxrDnStatTxStrength OBJECT-TYPE
    SYNTAX Integer32
    UNITS "dBm"
    MAX-ACCESS read-only
    STATUS current
    DESCRIPTION "Stat transmit signal strength (Nstreme Dual interface)."
    ::= { mtxrDnStatEntry 4 }

mtxrDnStatRxStrength OBJECT-TYPE
    SYNTAX Integer32
    UNITS "dBm"
    MAX-ACCESS read-only
    STATUS current
    DESCRIPTION "Stat receive signal strength (Nstreme Dual interface)."
    ::= { mtxrDnStatEntry 5 }

mtxrDnConnected OBJECT-TYPE
    SYNTAX Integer32
    MAX-ACCESS read-only
    STATUS current
    DESCRIPTION
        "Connection state: 0 = not connected, any other value = connected."
    ::= { mtxrDnStatEntry 6 }

mtxrNstremeDualGroup OBJECT-GROUP
    OBJECTS {
        mtxrDnStatTxRate,
        mtxrDnStatRxRate,
        mtxrDnStatTxStrength,
        mtxrDnStatRxStrength,
        mtxrDnConnected
    }
    STATUS current
    DESCRIPTION "Nstreme Dual interface statistics."
    ::= { mtXRouterOsGroups 10 }

-- NEIGHBOR *******************************************************************

mtxrNeighborTable OBJECT-TYPE
    SYNTAX SEQUENCE OF MtxrNeighborTableEntry
    MAX-ACCESS not-accessible
    STATUS current
    DESCRIPTION "Table of neighbor discovery entries."
    ::= { mtxrNeighbor 1 }

mtxrNeighborTableEntry OBJECT-TYPE
    SYNTAX MtxrNeighborTableEntry
    MAX-ACCESS not-accessible
    STATUS current
    DESCRIPTION "Entry of the neighbor discovery table."
    INDEX { mtxrNeighborIndex }
    ::= { mtxrNeighborTable 1 }

MtxrNeighborTableEntry ::= SEQUENCE {
        mtxrNeighborIndex ObjectIndex,
        mtxrNeighborIpAddress IpAddress,
        mtxrNeighborMacAddress MacAddress,
        mtxrNeighborVersion DisplayString,
        mtxrNeighborPlatform DisplayString,
        mtxrNeighborIdentity DisplayString,
        mtxrNeighborSoftwareID DisplayString,
        mtxrNeighborInterfaceID ObjectIndex
}

mtxrNeighborIndex OBJECT-TYPE
    SYNTAX ObjectIndex
    MAX-ACCESS not-accessible
    STATUS current
    DESCRIPTION
        "Index identifying the row (internal object ID, not the console
         item number)."
    ::= { mtxrNeighborTableEntry 1 }

mtxrNeighborIpAddress OBJECT-TYPE
    SYNTAX IpAddress
    MAX-ACCESS read-only
    STATUS current
    DESCRIPTION "IP address (neighbor discovery)."
    ::= { mtxrNeighborTableEntry 2 }

mtxrNeighborMacAddress OBJECT-TYPE
    SYNTAX MacAddress
    MAX-ACCESS read-only
    STATUS current
    DESCRIPTION "MAC address (neighbor discovery)."
    ::= { mtxrNeighborTableEntry 3 }

mtxrNeighborVersion OBJECT-TYPE
    SYNTAX DisplayString
    MAX-ACCESS read-only
    STATUS current
    DESCRIPTION "Version (neighbor discovery)."
    ::= { mtxrNeighborTableEntry 4 }

mtxrNeighborPlatform OBJECT-TYPE
    SYNTAX DisplayString
    MAX-ACCESS read-only
    STATUS current
    DESCRIPTION "Platform (neighbor discovery)."
    ::= { mtxrNeighborTableEntry 5 }

mtxrNeighborIdentity OBJECT-TYPE
    SYNTAX DisplayString
    MAX-ACCESS read-only
    STATUS current
    DESCRIPTION "Identity (neighbor discovery)."
    ::= { mtxrNeighborTableEntry 6 }

mtxrNeighborSoftwareID OBJECT-TYPE
    SYNTAX DisplayString
    MAX-ACCESS read-only
    STATUS current
    DESCRIPTION "Software ID (neighbor discovery)."
    ::= { mtxrNeighborTableEntry 7 }

mtxrNeighborInterfaceID OBJECT-TYPE
    SYNTAX ObjectIndex
    MAX-ACCESS read-only
    STATUS current
    DESCRIPTION "Interface ID (neighbor discovery)."
    ::= { mtxrNeighborTableEntry 8 }

mtxrNeighborGroup OBJECT-GROUP
    OBJECTS {
        mtxrNeighborIpAddress,
        mtxrNeighborMacAddress,
        mtxrNeighborVersion,
        mtxrNeighborPlatform,
        mtxrNeighborIdentity,
        mtxrNeighborSoftwareID,
        mtxrNeighborInterfaceID
    }
    STATUS current
    DESCRIPTION "Discovered neighbors."
    ::= { mtXRouterOsGroups 11 }

-- GPS ************************************************************************

mtxrDate OBJECT-TYPE
    SYNTAX Integer32
    UNITS "seconds"
    MAX-ACCESS read-only
    STATUS current
    DESCRIPTION
        "GPS date and time as UNIX time (seconds since 1970-01-01 UTC)."
    ::= { mtxrGps 1 }

mtxrLongtitude OBJECT-TYPE
    SYNTAX DisplayString
    MAX-ACCESS read-only
    STATUS current
    DESCRIPTION "Longtitude."
    ::= { mtxrGps 2 }

mtxrLatitude OBJECT-TYPE
    SYNTAX DisplayString
    MAX-ACCESS read-only
    STATUS current
    DESCRIPTION "Latitude."
    ::= { mtxrGps 3 }

mtxrAltitude OBJECT-TYPE
    SYNTAX DisplayString
    MAX-ACCESS read-only
    STATUS current
    DESCRIPTION "Altitude."
    ::= { mtxrGps 4 }

mtxrSpeed OBJECT-TYPE
    SYNTAX DisplayString
    MAX-ACCESS read-only
    STATUS current
    DESCRIPTION "Speed."
    ::= { mtxrGps 5 }

mtxrSattelites OBJECT-TYPE
    SYNTAX Integer32
    MAX-ACCESS read-only
    STATUS current
    DESCRIPTION "Number of visible GPS satellites."
    ::= { mtxrGps 6 }

mtxrValid OBJECT-TYPE
    SYNTAX Integer32
    MAX-ACCESS read-only
    STATUS current
    DESCRIPTION "GPS data validity: 0 = invalid, non-zero = valid."
    ::= { mtxrGps 7 }

mtxrGPSGroup OBJECT-GROUP
    OBJECTS {
        mtxrDate,
        mtxrLongtitude,
        mtxrLatitude,
        mtxrAltitude,
        mtxrSpeed,
        mtxrSattelites,
        mtxrValid
    }
    STATUS current
    DESCRIPTION "GPS position, speed and status."
    ::= { mtXRouterOsGroups 15 }

-- Wireless Modem ************************************************************

mtxrWirelessModemSignalStrength OBJECT-TYPE
    SYNTAX Integer32
    UNITS "dBm"
    MAX-ACCESS read-only
    STATUS current
    DESCRIPTION
        "Signal strength in dBm (if first ppp-client modem supports)"
    ::= { mtxrWirelessModem 1 }

mtxrWirelessModemSignalECIO OBJECT-TYPE
    SYNTAX Integer32
    UNITS "dB"
    MAX-ACCESS read-only
    STATUS current
    DESCRIPTION "Signal EC/IO in dB (if first ppp-client modem supports)"
    ::= { mtxrWirelessModem 2 }

mtxrWirelessModemManufacturer OBJECT-TYPE
    SYNTAX DisplayString
    MAX-ACCESS read-only
    STATUS current
    DESCRIPTION "Modem manufacturer name."
    ::= { mtxrWirelessModem 3 }

mtxrWirelessModemModel OBJECT-TYPE
    SYNTAX DisplayString
    MAX-ACCESS read-only
    STATUS current
    DESCRIPTION "Modem model name."
    ::= { mtxrWirelessModem 4 }

mtxrWirelessModemRevision OBJECT-TYPE
    SYNTAX DisplayString
    MAX-ACCESS read-only
    STATUS current
    DESCRIPTION "Modem firmware revision."
    ::= { mtxrWirelessModem 5 }

mtxrWirelessModemIMEI OBJECT-TYPE
    SYNTAX DisplayString
    MAX-ACCESS read-only
    STATUS current
    DESCRIPTION "Modem serial number."
    ::= { mtxrWirelessModem 6 }

mtxrWirelessModemIMSI OBJECT-TYPE
    SYNTAX DisplayString
    MAX-ACCESS read-only
    STATUS current
    DESCRIPTION "International mobile subscriber identity."
    ::= { mtxrWirelessModem 7 }

mtxrWirelessModemAccessTechnology OBJECT-TYPE
    SYNTAX DisplayString
    MAX-ACCESS read-only
    STATUS current
    DESCRIPTION "Access technology."
    ::= { mtxrWirelessModem 8 }

mtxrWirelessModemFrameErrorRate OBJECT-TYPE
    SYNTAX DisplayString
    MAX-ACCESS read-only
    STATUS current
    DESCRIPTION "Signal frame error rate."
    ::= { mtxrWirelessModem 9 }

mtxrWirelessModemRSRP OBJECT-TYPE
    SYNTAX Integer32
    UNITS "dBm"
    MAX-ACCESS read-only
    STATUS current
    DESCRIPTION "Reference Signal Receive Power."
    ::= { mtxrWirelessModem 10 }

mtxrWirelessModemRSRQ OBJECT-TYPE
    SYNTAX Integer32
    UNITS "dB"
    MAX-ACCESS read-only
    STATUS current
    DESCRIPTION "Reference Signal Received Quality."
    ::= { mtxrWirelessModem 11 }

mtxrWirelessModemSINR OBJECT-TYPE
    SYNTAX Integer32
    UNITS "dB"
    MAX-ACCESS read-only
    STATUS current
    DESCRIPTION "Signal-to-Interference-plus-Noise Ratio."
    ::= { mtxrWirelessModem 12 }

mtxrWirelessModemPinStatus OBJECT-TYPE
    SYNTAX DisplayString
    MAX-ACCESS read-only
    STATUS current
    DESCRIPTION "Pin status of the modem."
    ::= { mtxrWirelessModem 13 }

mtxrWirelessModemGroup OBJECT-GROUP
    OBJECTS {
        mtxrWirelessModemSignalStrength,
        mtxrWirelessModemSignalECIO,
        mtxrWirelessModemManufacturer,
        mtxrWirelessModemModel,
        mtxrWirelessModemRevision,
        mtxrWirelessModemIMEI,
        mtxrWirelessModemIMSI,
        mtxrWirelessModemAccessTechnology,
        mtxrWirelessModemFrameErrorRate,
        mtxrWirelessModemRSRP,
        mtxrWirelessModemRSRQ,
        mtxrWirelessModemSINR,
        mtxrWirelessModemPinStatus
    }
    STATUS current
    DESCRIPTION "PPP wireless modem information."
    ::= { mtXRouterOsGroups 16 }

-- Interface Stats ************************************************************

mtxrInterfaceStatsTable OBJECT-TYPE
    SYNTAX SEQUENCE OF MtxrInterfaceStatsEntry
    MAX-ACCESS not-accessible
    STATUS current
    DESCRIPTION
        "Extended interface statistics. Some interfaces may have only parts
         of this table with unavailable values set to zero."
    ::= { mtxrInterfaceStats 1 }

mtxrInterfaceStatsEntry OBJECT-TYPE
    SYNTAX MtxrInterfaceStatsEntry
    MAX-ACCESS not-accessible
    STATUS current
    DESCRIPTION "Entry of the interface statistics table."
    INDEX { mtxrInterfaceStatsIndex }
    ::= { mtxrInterfaceStatsTable 1 }

MtxrInterfaceStatsEntry ::= SEQUENCE {
    mtxrInterfaceStatsIndex ObjectIndex,
    mtxrInterfaceStatsName DisplayString,

    mtxrInterfaceStatsDriverRxBytes Counter64,
    mtxrInterfaceStatsDriverRxPackets Counter64,
    mtxrInterfaceStatsDriverTxBytes Counter64,
    mtxrInterfaceStatsDriverTxPackets Counter64,

    mtxrInterfaceStatsTxRx64 Counter64,
    mtxrInterfaceStatsTxRx65To127 Counter64,
    mtxrInterfaceStatsTxRx128To255 Counter64,
    mtxrInterfaceStatsTxRx256To511 Counter64,
    mtxrInterfaceStatsTxRx512To1023 Counter64,
    mtxrInterfaceStatsTxRx1024To1518 Counter64,
    mtxrInterfaceStatsTxRx1519ToMax Counter64,

    mtxrInterfaceStatsRxBytes Counter64,
    mtxrInterfaceStatsRxPackets Counter64,
    mtxrInterfaceStatsRxTooShort Counter64,
    mtxrInterfaceStatsRx64 Counter64,
    mtxrInterfaceStatsRx65To127 Counter64,
    mtxrInterfaceStatsRx128To255 Counter64,
    mtxrInterfaceStatsRx256To511 Counter64,
    mtxrInterfaceStatsRx512To1023 Counter64,
    mtxrInterfaceStatsRx1024To1518 Counter64,
    mtxrInterfaceStatsRx1519ToMax Counter64,
    mtxrInterfaceStatsRxTooLong Counter64,
    mtxrInterfaceStatsRxBroadcast Counter64,
    mtxrInterfaceStatsRxPause Counter64,
    mtxrInterfaceStatsRxMulticast Counter64,
    mtxrInterfaceStatsRxFCSError Counter64,
    mtxrInterfaceStatsRxAlignError Counter64,
    mtxrInterfaceStatsRxFragment Counter64,
    mtxrInterfaceStatsRxOverflow Counter64,
    mtxrInterfaceStatsRxControl Counter64,
    mtxrInterfaceStatsRxUnknownOp Counter64,
    mtxrInterfaceStatsRxLengthError Counter64,
    mtxrInterfaceStatsRxCodeError Counter64,
    mtxrInterfaceStatsRxCarrierError Counter64,
    mtxrInterfaceStatsRxJabber Counter64,
    mtxrInterfaceStatsRxDrop Counter64,

    mtxrInterfaceStatsTxBytes Counter64,
    mtxrInterfaceStatsTxPackets Counter64,
    mtxrInterfaceStatsTxTooShort Counter64,
    mtxrInterfaceStatsTx64 Counter64,
    mtxrInterfaceStatsTx65To127 Counter64,
    mtxrInterfaceStatsTx128To255 Counter64,
    mtxrInterfaceStatsTx256To511 Counter64,
    mtxrInterfaceStatsTx512To1023 Counter64,
    mtxrInterfaceStatsTx1024To1518 Counter64,
    mtxrInterfaceStatsTx1519ToMax Counter64,
    mtxrInterfaceStatsTxTooLong Counter64,
    mtxrInterfaceStatsTxBroadcast Counter64,
    mtxrInterfaceStatsTxPause Counter64,
    mtxrInterfaceStatsTxMulticast Counter64,
    mtxrInterfaceStatsTxUnderrun Counter64,
    mtxrInterfaceStatsTxCollision Counter64,
    mtxrInterfaceStatsTxExcessiveCollision Counter64,
    mtxrInterfaceStatsTxMultipleCollision Counter64,
    mtxrInterfaceStatsTxSingleCollision Counter64,
    mtxrInterfaceStatsTxExcessiveDeferred Counter64,
    mtxrInterfaceStatsTxDeferred Counter64,
    mtxrInterfaceStatsTxLateCollision Counter64,
    mtxrInterfaceStatsTxTotalCollision Counter64,
    mtxrInterfaceStatsTxPauseHonored Counter64,
    mtxrInterfaceStatsTxDrop Counter64,
    mtxrInterfaceStatsTxJabber Counter64,
    mtxrInterfaceStatsTxFCSError Counter64,
    mtxrInterfaceStatsTxControl Counter64,
    mtxrInterfaceStatsTxFragment Counter64,
    mtxrInterfaceStatsLinkDowns Counter32,
    mtxrInterfaceStatsTxRx1024ToMax Counter64
}

mtxrInterfaceStatsIndex OBJECT-TYPE
    SYNTAX ObjectIndex
    MAX-ACCESS not-accessible
    STATUS current
    DESCRIPTION
        "Index identifying the row (internal object ID, not the console
         item number)."
    ::= { mtxrInterfaceStatsEntry 1 }

mtxrInterfaceStatsName OBJECT-TYPE
    SYNTAX DisplayString
    MAX-ACCESS read-only
    STATUS current
    DESCRIPTION "Name (interface statistics)."
    ::= { mtxrInterfaceStatsEntry 2 }

mtxrInterfaceStatsDriverRxBytes OBJECT-TYPE
    SYNTAX Counter64
    UNITS "bytes"
    MAX-ACCESS read-only
    STATUS current
    DESCRIPTION "Driver receive bytes (interface statistics)."
    ::= { mtxrInterfaceStatsEntry 11 }

mtxrInterfaceStatsDriverRxPackets OBJECT-TYPE
    SYNTAX Counter64
    UNITS "packets"
    MAX-ACCESS read-only
    STATUS current
    DESCRIPTION "Driver receive packets (interface statistics)."
    ::= { mtxrInterfaceStatsEntry 12 }

mtxrInterfaceStatsDriverTxBytes OBJECT-TYPE
    SYNTAX Counter64
    UNITS "bytes"
    MAX-ACCESS read-only
    STATUS current
    DESCRIPTION "Driver transmit bytes (interface statistics)."
    ::= { mtxrInterfaceStatsEntry 13 }

mtxrInterfaceStatsDriverTxPackets OBJECT-TYPE
    SYNTAX Counter64
    UNITS "packets"
    MAX-ACCESS read-only
    STATUS current
    DESCRIPTION "Driver transmit packets (interface statistics)."
    ::= { mtxrInterfaceStatsEntry 14 }

mtxrInterfaceStatsTxRx64 OBJECT-TYPE
    SYNTAX Counter64
    MAX-ACCESS read-only
    STATUS current
    DESCRIPTION
        "Number of transmitted and received frames of exactly 64 bytes."
    ::= { mtxrInterfaceStatsEntry 15 }

mtxrInterfaceStatsTxRx65To127 OBJECT-TYPE
    SYNTAX Counter64
    MAX-ACCESS read-only
    STATUS current
    DESCRIPTION
        "Number of transmitted and received frames of 65 to 127 bytes."
    ::= { mtxrInterfaceStatsEntry 16 }

mtxrInterfaceStatsTxRx128To255 OBJECT-TYPE
    SYNTAX Counter64
    MAX-ACCESS read-only
    STATUS current
    DESCRIPTION
        "Number of transmitted and received frames of 128 to 255 bytes."
    ::= { mtxrInterfaceStatsEntry 17 }

mtxrInterfaceStatsTxRx256To511 OBJECT-TYPE
    SYNTAX Counter64
    MAX-ACCESS read-only
    STATUS current
    DESCRIPTION
        "Number of transmitted and received frames of 256 to 511 bytes."
    ::= { mtxrInterfaceStatsEntry 18 }

mtxrInterfaceStatsTxRx512To1023 OBJECT-TYPE
    SYNTAX Counter64
    MAX-ACCESS read-only
    STATUS current
    DESCRIPTION
        "Number of transmitted and received frames of 512 to 1023 bytes."
    ::= { mtxrInterfaceStatsEntry 19 }

mtxrInterfaceStatsTxRx1024To1518 OBJECT-TYPE
    SYNTAX Counter64
    MAX-ACCESS read-only
    STATUS current
    DESCRIPTION
        "Number of transmitted and received frames of 1024 to 1518 bytes."
    ::= { mtxrInterfaceStatsEntry 20 }

mtxrInterfaceStatsTxRx1519ToMax OBJECT-TYPE
    SYNTAX Counter64
    MAX-ACCESS read-only
    STATUS current
    DESCRIPTION
        "Number of transmitted and received frames of 1519 bytes or more."
    ::= { mtxrInterfaceStatsEntry 21 }

mtxrInterfaceStatsRxBytes OBJECT-TYPE
    SYNTAX Counter64
    UNITS "bytes"
    MAX-ACCESS read-only
    STATUS current
    DESCRIPTION "Receive bytes (interface statistics)."
    ::= { mtxrInterfaceStatsEntry 31 }

mtxrInterfaceStatsRxPackets OBJECT-TYPE
    SYNTAX Counter64
    UNITS "packets"
    MAX-ACCESS read-only
    STATUS current
    DESCRIPTION "Receive packets (interface statistics)."
    ::= { mtxrInterfaceStatsEntry 32 }

mtxrInterfaceStatsRxTooShort OBJECT-TYPE
    SYNTAX Counter64
    MAX-ACCESS read-only
    STATUS current
    DESCRIPTION "Receive too short (interface statistics)."
    ::= { mtxrInterfaceStatsEntry 33 }

mtxrInterfaceStatsRx64 OBJECT-TYPE
    SYNTAX Counter64
    MAX-ACCESS read-only
    STATUS current
    DESCRIPTION "Number of received frames of exactly 64 bytes."
    ::= { mtxrInterfaceStatsEntry 34 }

mtxrInterfaceStatsRx65To127 OBJECT-TYPE
    SYNTAX Counter64
    MAX-ACCESS read-only
    STATUS current
    DESCRIPTION "Number of received frames of 65 to 127 bytes."
    ::= { mtxrInterfaceStatsEntry 35 }

mtxrInterfaceStatsRx128To255 OBJECT-TYPE
    SYNTAX Counter64
    MAX-ACCESS read-only
    STATUS current
    DESCRIPTION "Number of received frames of 128 to 255 bytes."
    ::= { mtxrInterfaceStatsEntry 36 }

mtxrInterfaceStatsRx256To511 OBJECT-TYPE
    SYNTAX Counter64
    MAX-ACCESS read-only
    STATUS current
    DESCRIPTION "Number of received frames of 256 to 511 bytes."
    ::= { mtxrInterfaceStatsEntry 37 }

mtxrInterfaceStatsRx512To1023 OBJECT-TYPE
    SYNTAX Counter64
    MAX-ACCESS read-only
    STATUS current
    DESCRIPTION "Number of received frames of 512 to 1023 bytes."
    ::= { mtxrInterfaceStatsEntry 38 }

mtxrInterfaceStatsRx1024To1518 OBJECT-TYPE
    SYNTAX Counter64
    MAX-ACCESS read-only
    STATUS current
    DESCRIPTION "Number of received frames of 1024 to 1518 bytes."
    ::= { mtxrInterfaceStatsEntry 39 }

mtxrInterfaceStatsRx1519ToMax OBJECT-TYPE
    SYNTAX Counter64
    MAX-ACCESS read-only
    STATUS current
    DESCRIPTION "Number of received frames of 1519 bytes or more."
    ::= { mtxrInterfaceStatsEntry 40 }

mtxrInterfaceStatsRxTooLong OBJECT-TYPE
    SYNTAX Counter64
    MAX-ACCESS read-only
    STATUS current
    DESCRIPTION "Receive too long (interface statistics)."
    ::= { mtxrInterfaceStatsEntry 41 }

mtxrInterfaceStatsRxBroadcast OBJECT-TYPE
    SYNTAX Counter64
    MAX-ACCESS read-only
    STATUS current
    DESCRIPTION "Receive broadcast (interface statistics)."
    ::= { mtxrInterfaceStatsEntry 42 }

mtxrInterfaceStatsRxPause OBJECT-TYPE
    SYNTAX Counter64
    MAX-ACCESS read-only
    STATUS current
    DESCRIPTION "Receive pause (interface statistics)."
    ::= { mtxrInterfaceStatsEntry 43 }

mtxrInterfaceStatsRxMulticast OBJECT-TYPE
    SYNTAX Counter64
    MAX-ACCESS read-only
    STATUS current
    DESCRIPTION "Receive multicast (interface statistics)."
    ::= { mtxrInterfaceStatsEntry 44 }

mtxrInterfaceStatsRxFCSError OBJECT-TYPE
    SYNTAX Counter64
    MAX-ACCESS read-only
    STATUS current
    DESCRIPTION "Receive FCS error (interface statistics)."
    ::= { mtxrInterfaceStatsEntry 45 }

mtxrInterfaceStatsRxAlignError OBJECT-TYPE
    SYNTAX Counter64
    MAX-ACCESS read-only
    STATUS current
    DESCRIPTION "Receive align error (interface statistics)."
    ::= { mtxrInterfaceStatsEntry 46 }

mtxrInterfaceStatsRxFragment OBJECT-TYPE
    SYNTAX Counter64
    MAX-ACCESS read-only
    STATUS current
    DESCRIPTION "Receive fragment (interface statistics)."
    ::= { mtxrInterfaceStatsEntry 47 }

mtxrInterfaceStatsRxOverflow OBJECT-TYPE
    SYNTAX Counter64
    MAX-ACCESS read-only
    STATUS current
    DESCRIPTION "Receive overflow (interface statistics)."
    ::= { mtxrInterfaceStatsEntry 48 }

mtxrInterfaceStatsRxControl OBJECT-TYPE
    SYNTAX Counter64
    MAX-ACCESS read-only
    STATUS current
    DESCRIPTION "Receive control (interface statistics)."
    ::= { mtxrInterfaceStatsEntry 49 }

mtxrInterfaceStatsRxUnknownOp OBJECT-TYPE
    SYNTAX Counter64
    MAX-ACCESS read-only
    STATUS current
    DESCRIPTION "Receive unknown opcode (interface statistics)."
    ::= { mtxrInterfaceStatsEntry 50 }

mtxrInterfaceStatsRxLengthError OBJECT-TYPE
    SYNTAX Counter64
    MAX-ACCESS read-only
    STATUS current
    DESCRIPTION "Receive length error (interface statistics)."
    ::= { mtxrInterfaceStatsEntry 51 }

mtxrInterfaceStatsRxCodeError OBJECT-TYPE
    SYNTAX Counter64
    MAX-ACCESS read-only
    STATUS current
    DESCRIPTION "Receive code error (interface statistics)."
    ::= { mtxrInterfaceStatsEntry 52 }

mtxrInterfaceStatsRxCarrierError OBJECT-TYPE
    SYNTAX Counter64
    MAX-ACCESS read-only
    STATUS current
    DESCRIPTION "Receive carrier error (interface statistics)."
    ::= { mtxrInterfaceStatsEntry 53 }

mtxrInterfaceStatsRxJabber OBJECT-TYPE
    SYNTAX Counter64
    MAX-ACCESS read-only
    STATUS current
    DESCRIPTION "Receive jabber (interface statistics)."
    ::= { mtxrInterfaceStatsEntry 54 }

mtxrInterfaceStatsRxDrop OBJECT-TYPE
    SYNTAX Counter64
    MAX-ACCESS read-only
    STATUS current
    DESCRIPTION "Receive drop (interface statistics)."
    ::= { mtxrInterfaceStatsEntry 55 }

mtxrInterfaceStatsTxBytes OBJECT-TYPE
    SYNTAX Counter64
    UNITS "bytes"
    MAX-ACCESS read-only
    STATUS current
    DESCRIPTION "Transmit bytes (interface statistics)."
    ::= { mtxrInterfaceStatsEntry 61 }

mtxrInterfaceStatsTxPackets OBJECT-TYPE
    SYNTAX Counter64
    UNITS "packets"
    MAX-ACCESS read-only
    STATUS current
    DESCRIPTION "Transmit packets (interface statistics)."
    ::= { mtxrInterfaceStatsEntry 62 }

mtxrInterfaceStatsTxTooShort OBJECT-TYPE
    SYNTAX Counter64
    MAX-ACCESS read-only
    STATUS current
    DESCRIPTION "Transmit too short (interface statistics)."
    ::= { mtxrInterfaceStatsEntry 63 }

mtxrInterfaceStatsTx64 OBJECT-TYPE
    SYNTAX Counter64
    MAX-ACCESS read-only
    STATUS current
    DESCRIPTION "Number of transmitted frames of exactly 64 bytes."
    ::= { mtxrInterfaceStatsEntry 64 }

mtxrInterfaceStatsTx65To127 OBJECT-TYPE
    SYNTAX Counter64
    MAX-ACCESS read-only
    STATUS current
    DESCRIPTION "Number of transmitted frames of 65 to 127 bytes."
    ::= { mtxrInterfaceStatsEntry 65 }

mtxrInterfaceStatsTx128To255 OBJECT-TYPE
    SYNTAX Counter64
    MAX-ACCESS read-only
    STATUS current
    DESCRIPTION "Number of transmitted frames of 128 to 255 bytes."
    ::= { mtxrInterfaceStatsEntry 66 }

mtxrInterfaceStatsTx256To511 OBJECT-TYPE
    SYNTAX Counter64
    MAX-ACCESS read-only
    STATUS current
    DESCRIPTION "Number of transmitted frames of 256 to 511 bytes."
    ::= { mtxrInterfaceStatsEntry 67 }

mtxrInterfaceStatsTx512To1023 OBJECT-TYPE
    SYNTAX Counter64
    MAX-ACCESS read-only
    STATUS current
    DESCRIPTION "Number of transmitted frames of 512 to 1023 bytes."
    ::= { mtxrInterfaceStatsEntry 68 }

mtxrInterfaceStatsTx1024To1518 OBJECT-TYPE
    SYNTAX Counter64
    MAX-ACCESS read-only
    STATUS current
    DESCRIPTION "Number of transmitted frames of 1024 to 1518 bytes."
    ::= { mtxrInterfaceStatsEntry 69 }

mtxrInterfaceStatsTx1519ToMax OBJECT-TYPE
    SYNTAX Counter64
    MAX-ACCESS read-only
    STATUS current
    DESCRIPTION "Number of transmitted frames of 1519 bytes or more."
    ::= { mtxrInterfaceStatsEntry 70 }

mtxrInterfaceStatsTxTooLong OBJECT-TYPE
    SYNTAX Counter64
    MAX-ACCESS read-only
    STATUS current
    DESCRIPTION "Transmit too long (interface statistics)."
    ::= { mtxrInterfaceStatsEntry 71 }

mtxrInterfaceStatsTxBroadcast OBJECT-TYPE
    SYNTAX Counter64
    MAX-ACCESS read-only
    STATUS current
    DESCRIPTION "Transmit broadcast (interface statistics)."
    ::= { mtxrInterfaceStatsEntry 72 }

mtxrInterfaceStatsTxPause OBJECT-TYPE
    SYNTAX Counter64
    MAX-ACCESS read-only
    STATUS current
    DESCRIPTION "Transmit pause (interface statistics)."
    ::= { mtxrInterfaceStatsEntry 73 }

mtxrInterfaceStatsTxMulticast OBJECT-TYPE
    SYNTAX Counter64
    MAX-ACCESS read-only
    STATUS current
    DESCRIPTION "Transmit multicast (interface statistics)."
    ::= { mtxrInterfaceStatsEntry 74 }

mtxrInterfaceStatsTxUnderrun OBJECT-TYPE
    SYNTAX Counter64
    MAX-ACCESS read-only
    STATUS current
    DESCRIPTION "Transmit underrun (interface statistics)."
    ::= { mtxrInterfaceStatsEntry 75 }

mtxrInterfaceStatsTxCollision OBJECT-TYPE
    SYNTAX Counter64
    MAX-ACCESS read-only
    STATUS current
    DESCRIPTION "Transmit collision (interface statistics)."
    ::= { mtxrInterfaceStatsEntry 76 }

mtxrInterfaceStatsTxExcessiveCollision OBJECT-TYPE
    SYNTAX Counter64
    MAX-ACCESS read-only
    STATUS current
    DESCRIPTION "Transmit excessive collision (interface statistics)."
    ::= { mtxrInterfaceStatsEntry 77 }

mtxrInterfaceStatsTxMultipleCollision OBJECT-TYPE
    SYNTAX Counter64
    MAX-ACCESS read-only
    STATUS current
    DESCRIPTION "Transmit multiple collision (interface statistics)."
    ::= { mtxrInterfaceStatsEntry 78 }

mtxrInterfaceStatsTxSingleCollision OBJECT-TYPE
    SYNTAX Counter64
    MAX-ACCESS read-only
    STATUS current
    DESCRIPTION "Transmit single collision (interface statistics)."
    ::= { mtxrInterfaceStatsEntry 79 }

mtxrInterfaceStatsTxExcessiveDeferred OBJECT-TYPE
    SYNTAX Counter64
    MAX-ACCESS read-only
    STATUS current
    DESCRIPTION "Transmit excessive deferred (interface statistics)."
    ::= { mtxrInterfaceStatsEntry 80 }

mtxrInterfaceStatsTxDeferred OBJECT-TYPE
    SYNTAX Counter64
    MAX-ACCESS read-only
    STATUS current
    DESCRIPTION "Transmit deferred (interface statistics)."
    ::= { mtxrInterfaceStatsEntry 81 }

mtxrInterfaceStatsTxLateCollision OBJECT-TYPE
    SYNTAX Counter64
    MAX-ACCESS read-only
    STATUS current
    DESCRIPTION "Transmit late collision (interface statistics)."
    ::= { mtxrInterfaceStatsEntry 82 }

mtxrInterfaceStatsTxTotalCollision OBJECT-TYPE
    SYNTAX Counter64
    MAX-ACCESS read-only
    STATUS current
    DESCRIPTION "Transmit total collision (interface statistics)."
    ::= { mtxrInterfaceStatsEntry 83 }

mtxrInterfaceStatsTxPauseHonored OBJECT-TYPE
    SYNTAX Counter64
    MAX-ACCESS read-only
    STATUS current
    DESCRIPTION "Transmit pause honored (interface statistics)."
    ::= { mtxrInterfaceStatsEntry 84 }

mtxrInterfaceStatsTxDrop OBJECT-TYPE
    SYNTAX Counter64
    MAX-ACCESS read-only
    STATUS current
    DESCRIPTION "Transmit drop (interface statistics)."
    ::= { mtxrInterfaceStatsEntry 85 }

mtxrInterfaceStatsTxJabber OBJECT-TYPE
    SYNTAX Counter64
    MAX-ACCESS read-only
    STATUS current
    DESCRIPTION "Transmit jabber (interface statistics)."
    ::= { mtxrInterfaceStatsEntry 86 }

mtxrInterfaceStatsTxFCSError OBJECT-TYPE
    SYNTAX Counter64
    MAX-ACCESS read-only
    STATUS current
    DESCRIPTION "Transmit FCS error (interface statistics)."
    ::= { mtxrInterfaceStatsEntry 87 }

mtxrInterfaceStatsTxControl OBJECT-TYPE
    SYNTAX Counter64
    MAX-ACCESS read-only
    STATUS current
    DESCRIPTION "Transmit control (interface statistics)."
    ::= { mtxrInterfaceStatsEntry 88 }

mtxrInterfaceStatsTxFragment OBJECT-TYPE
    SYNTAX Counter64
    MAX-ACCESS read-only
    STATUS current
    DESCRIPTION "Transmit fragment (interface statistics)."
    ::= { mtxrInterfaceStatsEntry 89 }

mtxrInterfaceStatsLinkDowns OBJECT-TYPE
    SYNTAX Counter32
    MAX-ACCESS read-only
    STATUS current
    DESCRIPTION "Link downs (interface statistics)."
    ::= { mtxrInterfaceStatsEntry 90 }

mtxrInterfaceStatsTxRx1024ToMax OBJECT-TYPE
    SYNTAX Counter64
    MAX-ACCESS read-only
    STATUS current
    DESCRIPTION
        "Number of transmitted and received frames of 1024 bytes or more."
    ::= { mtxrInterfaceStatsEntry 91 }

mtxrInterfaceStatsGroup OBJECT-GROUP
    OBJECTS {
        mtxrInterfaceStatsName,
        mtxrInterfaceStatsDriverRxBytes,
        mtxrInterfaceStatsDriverRxPackets,
        mtxrInterfaceStatsDriverTxBytes,
        mtxrInterfaceStatsDriverTxPackets,
        mtxrInterfaceStatsTxRx64,
        mtxrInterfaceStatsTxRx65To127,
        mtxrInterfaceStatsTxRx128To255,
        mtxrInterfaceStatsTxRx256To511,
        mtxrInterfaceStatsTxRx512To1023,
        mtxrInterfaceStatsTxRx1024To1518,
        mtxrInterfaceStatsTxRx1519ToMax,
        mtxrInterfaceStatsRxBytes,
        mtxrInterfaceStatsRxPackets,
        mtxrInterfaceStatsRxTooShort,
        mtxrInterfaceStatsRx64,
        mtxrInterfaceStatsRx65To127,
        mtxrInterfaceStatsRx128To255,
        mtxrInterfaceStatsRx256To511,
        mtxrInterfaceStatsRx512To1023,
        mtxrInterfaceStatsRx1024To1518,
        mtxrInterfaceStatsRx1519ToMax,
        mtxrInterfaceStatsRxTooLong,
        mtxrInterfaceStatsRxBroadcast,
        mtxrInterfaceStatsRxPause,
        mtxrInterfaceStatsRxMulticast,
        mtxrInterfaceStatsRxFCSError,
        mtxrInterfaceStatsRxAlignError,
        mtxrInterfaceStatsRxFragment,
        mtxrInterfaceStatsRxOverflow,
        mtxrInterfaceStatsRxControl,
        mtxrInterfaceStatsRxUnknownOp,
        mtxrInterfaceStatsRxLengthError,
        mtxrInterfaceStatsRxCodeError,
        mtxrInterfaceStatsRxCarrierError,
        mtxrInterfaceStatsRxJabber,
        mtxrInterfaceStatsRxDrop,
        mtxrInterfaceStatsTxBytes,
        mtxrInterfaceStatsTxPackets,
        mtxrInterfaceStatsTxTooShort,
        mtxrInterfaceStatsTx64,
        mtxrInterfaceStatsTx65To127,
        mtxrInterfaceStatsTx128To255,
        mtxrInterfaceStatsTx256To511,
        mtxrInterfaceStatsTx512To1023,
        mtxrInterfaceStatsTx1024To1518,
        mtxrInterfaceStatsTx1519ToMax,
        mtxrInterfaceStatsTxTooLong,
        mtxrInterfaceStatsTxBroadcast,
        mtxrInterfaceStatsTxPause,
        mtxrInterfaceStatsTxMulticast,
        mtxrInterfaceStatsTxUnderrun,
        mtxrInterfaceStatsTxCollision,
        mtxrInterfaceStatsTxExcessiveCollision,
        mtxrInterfaceStatsTxMultipleCollision,
        mtxrInterfaceStatsTxSingleCollision,
        mtxrInterfaceStatsTxExcessiveDeferred,
        mtxrInterfaceStatsTxDeferred,
        mtxrInterfaceStatsTxLateCollision,
        mtxrInterfaceStatsTxTotalCollision,
        mtxrInterfaceStatsTxPauseHonored,
        mtxrInterfaceStatsTxDrop,
        mtxrInterfaceStatsTxJabber,
        mtxrInterfaceStatsTxFCSError,
        mtxrInterfaceStatsTxControl,
        mtxrInterfaceStatsTxFragment,
        mtxrInterfaceStatsLinkDowns,
        mtxrInterfaceStatsTxRx1024ToMax
    }
    STATUS current
    DESCRIPTION "Extended per-interface counters."
    ::= { mtXRouterOsGroups 17 }

-- POE ************************************************************************

mtxrPOETable OBJECT-TYPE
    SYNTAX SEQUENCE OF MtxrPOEEntry
    MAX-ACCESS not-accessible
    STATUS current
    DESCRIPTION "Power Over Ethernet."
    ::= { mtxrPOE 1 }

mtxrPOEEntry OBJECT-TYPE
    SYNTAX MtxrPOEEntry
    MAX-ACCESS not-accessible
    STATUS current
    DESCRIPTION "Entry of the PoE port table."
    INDEX { mtxrPOEInterfaceIndex }
    ::= { mtxrPOETable 1 }

MtxrPOEEntry ::= SEQUENCE {
    mtxrPOEInterfaceIndex ObjectIndex,
    mtxrPOEName DisplayString,
    mtxrPOEStatus INTEGER,
    mtxrPOEVoltage Voltage,
    mtxrPOECurrent Integer32,
    mtxrPOEPower Power
}

mtxrPOEInterfaceIndex OBJECT-TYPE
    SYNTAX ObjectIndex
    MAX-ACCESS not-accessible
    STATUS current
    DESCRIPTION
        "Index identifying the row (internal object ID, not the console
         item number)."
    ::= { mtxrPOEEntry 1 }

mtxrPOEName OBJECT-TYPE
    SYNTAX DisplayString
    MAX-ACCESS read-only
    STATUS current
    DESCRIPTION "Name (PoE port)."
    ::= { mtxrPOEEntry 2 }

mtxrPOEStatus OBJECT-TYPE
    SYNTAX INTEGER {
        disabled(1),
        waitingForLoad(2),
        poweredOn(3),
        overload(4),
        shortCircuit(5),
        voltageTooLow(6),
        currentTooLow(7),
        powerReset(8),
        voltageTooHigh(9),
        controllerError(10),
        controllerUpgrade(11),
        poeInDetected(12),
        noValidPsu(13),
        controllerInit(14),
        lowVoltageTooLow(15)
    }
    MAX-ACCESS read-only
    STATUS current
    DESCRIPTION "Status (PoE port)."
    ::= { mtxrPOEEntry 3 }

mtxrPOEVoltage OBJECT-TYPE
    SYNTAX Voltage
    UNITS "V"
    MAX-ACCESS read-only
    STATUS current
    DESCRIPTION "Voltage (PoE port)."
    ::= { mtxrPOEEntry 4 }

mtxrPOECurrent OBJECT-TYPE
    SYNTAX Integer32
    UNITS "mA"
    MAX-ACCESS read-only
    STATUS current
    DESCRIPTION "Current (PoE port)."
    ::= { mtxrPOEEntry 5 }

mtxrPOEPower OBJECT-TYPE
    SYNTAX Power
    UNITS "W"
    MAX-ACCESS read-only
    STATUS current
    DESCRIPTION "Power (PoE port)."
    ::= { mtxrPOEEntry 6 }

mtxrPOEGroup OBJECT-GROUP
    OBJECTS {
        mtxrPOEName,
        mtxrPOEStatus,
        mtxrPOEVoltage,
        mtxrPOECurrent,
        mtxrPOEPower
    }
    STATUS current
    DESCRIPTION "Power over Ethernet port status and measurements."
    ::= { mtXRouterOsGroups 18 }

-- LTE Modem ************************************************************

mtxrLTEModemTable OBJECT-TYPE
    SYNTAX SEQUENCE OF MtxrLTEModemEntry
    MAX-ACCESS not-accessible
    STATUS current
    DESCRIPTION "LTE Modems."
    ::= { mtxrLTEModem 1 }

mtxrLTEModemEntry OBJECT-TYPE
    SYNTAX MtxrLTEModemEntry
    MAX-ACCESS not-accessible
    STATUS current
    DESCRIPTION "Entry of the LTE modem table."
    INDEX { mtxrLTEModemInterfaceIndex }
    ::= { mtxrLTEModemTable 1 }

MtxrLTEModemEntry ::= SEQUENCE {
    mtxrLTEModemInterfaceIndex ObjectIndex,
    mtxrLTEModemSignalRSSI Integer32,
    mtxrLTEModemSignalRSRQ Integer32,
    mtxrLTEModemSignalRSRP Integer32,
    mtxrLTEModemCellId HexInt,
    mtxrLTEModemAccessTechnology INTEGER,
    mtxrLTEModemSignalSINR Integer32,
    mtxrLTEModemEnbId Integer32,
    mtxrLTEModemSectorId Integer32,
    mtxrLTEModemLac Integer32,
    mtxrLTEModemIMEI DisplayString,
    mtxrLTEModemIMSI DisplayString,
    mtxrLTEModemUICC DisplayString,
    mtxrLTEModemRAT DisplayString,
    mtxrLTEModemPrimaryBand DisplayString,
    mtxrLTEModemSessionUptime TimeTicks,
    mtxrLTEModemRegStatus DisplayString,
    mtxrLTEModemPinStatus DisplayString,
    mtxrLTEModemModel DisplayString,
    mtxrLTEModemFirmware DisplayString,
    mtxrLTEModemCQI Integer32,
    mtxrLTEModemNrRSRP Integer32,
    mtxrLTEModemNrRSRQ IDiv10,
    mtxrLTEModemNrSINR Integer32,
    mtxrLTEModemSignalRSRQD10 IDiv10
}

mtxrLTEModemInterfaceIndex OBJECT-TYPE
    SYNTAX ObjectIndex
    MAX-ACCESS not-accessible
    STATUS current
    DESCRIPTION
        "Index identifying the row (internal object ID, not the console
         item number)."
    ::= { mtxrLTEModemEntry 1 }

mtxrLTEModemSignalRSSI OBJECT-TYPE
    SYNTAX Integer32
    UNITS "dBm"
    MAX-ACCESS read-only
    STATUS current
    DESCRIPTION "Signal RSSI (LTE modem)."
    ::= { mtxrLTEModemEntry 2 }

mtxrLTEModemSignalRSRQ OBJECT-TYPE
    SYNTAX Integer32
    UNITS "dB"
    MAX-ACCESS read-only
    STATUS deprecated
    DESCRIPTION "Signal RSRQ (LTE modem)."
    ::= { mtxrLTEModemEntry 3 }

mtxrLTEModemSignalRSRP OBJECT-TYPE
    SYNTAX Integer32
    UNITS "dBm"
    MAX-ACCESS read-only
    STATUS current
    DESCRIPTION "Signal RSRP (LTE modem)."
    ::= { mtxrLTEModemEntry 4 }

mtxrLTEModemCellId OBJECT-TYPE
    SYNTAX HexInt
    MAX-ACCESS read-only
    STATUS current
    DESCRIPTION "Current cell ID."
    ::= { mtxrLTEModemEntry 5 }

mtxrLTEModemAccessTechnology OBJECT-TYPE
    SYNTAX INTEGER {
        unknown(-1),
        gsmcompact(0),
        gsm(1),
        utran(2),
        egprs(3),
        hsdpa(4),
        hsupa(5),
        hsdpahsupa(6),
        eutran(7),
        nr-sa(11),
        nr-nsa(13)
    }
    MAX-ACCESS read-only
    STATUS current
    DESCRIPTION "Current radio access technology, as reported by +CREG."
    ::= { mtxrLTEModemEntry 6 }

mtxrLTEModemSignalSINR OBJECT-TYPE
    SYNTAX Integer32
    UNITS "dB"
    MAX-ACCESS read-only
    STATUS current
    DESCRIPTION "Signal SINR (LTE modem)."
    ::= { mtxrLTEModemEntry 7 }

mtxrLTEModemEnbId OBJECT-TYPE
    SYNTAX Integer32
    MAX-ACCESS read-only
    STATUS current
    DESCRIPTION "ENodeB ID (LTE modem)."
    ::= { mtxrLTEModemEntry 8 }

mtxrLTEModemSectorId OBJECT-TYPE
    SYNTAX Integer32
    MAX-ACCESS read-only
    STATUS current
    DESCRIPTION "Sector ID (LTE modem)."
    ::= { mtxrLTEModemEntry 9 }

mtxrLTEModemLac OBJECT-TYPE
    SYNTAX Integer32
    MAX-ACCESS read-only
    STATUS current
    DESCRIPTION "LAC (LTE modem)."
    ::= { mtxrLTEModemEntry 10 }

mtxrLTEModemIMEI OBJECT-TYPE
    SYNTAX DisplayString
    MAX-ACCESS read-only
    STATUS current
    DESCRIPTION "IMEI (LTE modem)."
    ::= { mtxrLTEModemEntry 11 }

mtxrLTEModemIMSI OBJECT-TYPE
    SYNTAX DisplayString
    MAX-ACCESS read-only
    STATUS current
    DESCRIPTION "IMSI (LTE modem)."
    ::= { mtxrLTEModemEntry 12 }

mtxrLTEModemUICC OBJECT-TYPE
    SYNTAX DisplayString
    MAX-ACCESS read-only
    STATUS current
    DESCRIPTION "UICC (LTE modem)."
    ::= { mtxrLTEModemEntry 13 }

mtxrLTEModemRAT OBJECT-TYPE
    SYNTAX DisplayString
    MAX-ACCESS read-only
    STATUS current
    DESCRIPTION "RAT (LTE modem)."
    ::= { mtxrLTEModemEntry 14 }

mtxrLTEModemPrimaryBand OBJECT-TYPE
    SYNTAX DisplayString
    MAX-ACCESS read-only
    STATUS current
    DESCRIPTION "Primary band (LTE modem)."
    ::= { mtxrLTEModemEntry 15 }

mtxrLTEModemSessionUptime OBJECT-TYPE
    SYNTAX TimeTicks
    MAX-ACCESS read-only
    STATUS current
    DESCRIPTION "Session uptime (LTE modem)."
    ::= { mtxrLTEModemEntry 16 }

mtxrLTEModemRegStatus OBJECT-TYPE
    SYNTAX DisplayString
    MAX-ACCESS read-only
    STATUS current
    DESCRIPTION "Reg status (LTE modem)."
    ::= { mtxrLTEModemEntry 17 }

mtxrLTEModemPinStatus OBJECT-TYPE
    SYNTAX DisplayString
    MAX-ACCESS read-only
    STATUS current
    DESCRIPTION "PIN status (LTE modem)."
    ::= { mtxrLTEModemEntry 18 }

mtxrLTEModemModel OBJECT-TYPE
    SYNTAX DisplayString
    MAX-ACCESS read-only
    STATUS current
    DESCRIPTION "Model (LTE modem)."
    ::= { mtxrLTEModemEntry 19 }

mtxrLTEModemFirmware OBJECT-TYPE
    SYNTAX DisplayString
    MAX-ACCESS read-only
    STATUS current
    DESCRIPTION "Firmware (LTE modem)."
    ::= { mtxrLTEModemEntry 20 }

mtxrLTEModemCQI OBJECT-TYPE
    SYNTAX Integer32
    MAX-ACCESS read-only
    STATUS current
    DESCRIPTION "CQI (LTE modem)."
    ::= { mtxrLTEModemEntry 21 }

mtxrLTEModemNrRSRP OBJECT-TYPE
    SYNTAX Integer32
    UNITS "dBm"
    MAX-ACCESS read-only
    STATUS current
    DESCRIPTION "NR RSRP (LTE modem)."
    ::= { mtxrLTEModemEntry 22 }

mtxrLTEModemNrRSRQ OBJECT-TYPE
    SYNTAX IDiv10
    UNITS "dB"
    MAX-ACCESS read-only
    STATUS current
    DESCRIPTION "NR RSRQ (LTE modem)."
    ::= { mtxrLTEModemEntry 23 }

mtxrLTEModemNrSINR OBJECT-TYPE
    SYNTAX Integer32
    UNITS "dB"
    MAX-ACCESS read-only
    STATUS current
    DESCRIPTION "NR SINR (LTE modem)."
    ::= { mtxrLTEModemEntry 24 }

mtxrLTEModemSignalRSRQD10 OBJECT-TYPE
    SYNTAX IDiv10
    UNITS "dB"
    MAX-ACCESS read-only
    STATUS current
    DESCRIPTION "Signal RSRQD 10 (LTE modem)."
    ::= { mtxrLTEModemEntry 25 }

mtxrLTEModemGroup OBJECT-GROUP
    OBJECTS {
        mtxrLTEModemSignalRSSI,
        mtxrLTEModemSignalRSRQ,
        mtxrLTEModemSignalRSRP,
        mtxrLTEModemCellId,
        mtxrLTEModemAccessTechnology,
        mtxrLTEModemSignalSINR,
        mtxrLTEModemEnbId,
        mtxrLTEModemSectorId,
        mtxrLTEModemLac,
        mtxrLTEModemIMEI,
        mtxrLTEModemIMSI,
        mtxrLTEModemUICC,
        mtxrLTEModemRAT,
        mtxrLTEModemPrimaryBand,
        mtxrLTEModemSessionUptime,
        mtxrLTEModemRegStatus,
        mtxrLTEModemPinStatus,
        mtxrLTEModemModel,
        mtxrLTEModemFirmware,
        mtxrLTEModemCQI,
        mtxrLTEModemNrRSRP,
        mtxrLTEModemNrRSRQ,
        mtxrLTEModemNrSINR,
        mtxrLTEModemSignalRSRQD10
    }
    STATUS current
    DESCRIPTION "LTE modem signal and identity information."
    ::= { mtXRouterOsGroups 19 }

mtxrLTECarrierAgg OBJECT IDENTIFIER ::= { mtxrLTEModem 2 }

mtxrLTECarrierAggTable OBJECT-TYPE
    SYNTAX SEQUENCE OF MtxrLTECarrierAggEntry
    MAX-ACCESS not-accessible
    STATUS current
    DESCRIPTION "Table of LTE carrier aggregation entries."
    ::= { mtxrLTECarrierAgg 1 }

mtxrLTECarrierAggEntry OBJECT-TYPE
    SYNTAX MtxrLTECarrierAggEntry
    MAX-ACCESS not-accessible
    STATUS current
    DESCRIPTION "Entry of the LTE carrier aggregation table."
    INDEX {
        mtxrLTECarrierAggInterfaceIndex,
        mtxrLTECarrierAggIndex
    }
    ::= { mtxrLTECarrierAggTable 1 }

MtxrLTECarrierAggEntry ::= SEQUENCE {
    mtxrLTECarrierAggInterfaceIndex ObjectIndex,
    mtxrLTECarrierAggIndex ObjectIndex,
    mtxrLTECarrierAggBand Integer32,
    mtxrLTECarrierAggEARFCN Integer32,
    mtxrLTECarrierAggBandwidth Integer32,
    mtxrLTECarrierAggPhyCellId Integer32,
    mtxrLTECarrierAggRSSI Integer32,
    mtxrLTECarrierAggRSRP Integer32,
    mtxrLTECarrierAggRSRQ IDiv10,
    mtxrLTECarrierAggSINR Integer32,
    mtxrLTECarrierAggSNR Integer32,
    mtxrLTECarrierAggNR TruthValue,
    mtxrLTECarrierAggUplink TruthValue
}

mtxrLTECarrierAggInterfaceIndex OBJECT-TYPE
    SYNTAX ObjectIndex
    MAX-ACCESS not-accessible
    STATUS current
    DESCRIPTION
        "Index identifying the row (internal object ID, not the console
         item number)."
    ::= { mtxrLTECarrierAggEntry 1 }

mtxrLTECarrierAggIndex OBJECT-TYPE
    SYNTAX ObjectIndex
    MAX-ACCESS not-accessible
    STATUS current
    DESCRIPTION
        "Index identifying the row (internal object ID, not the console
         item number)."
    ::= { mtxrLTECarrierAggEntry 2 }

mtxrLTECarrierAggBand OBJECT-TYPE
    SYNTAX Integer32
    MAX-ACCESS read-only
    STATUS current
    DESCRIPTION "Band (LTE carrier aggregation)."
    ::= { mtxrLTECarrierAggEntry 3 }

mtxrLTECarrierAggEARFCN OBJECT-TYPE
    SYNTAX Integer32
    MAX-ACCESS read-only
    STATUS current
    DESCRIPTION "EARFCN (LTE carrier aggregation)."
    ::= { mtxrLTECarrierAggEntry 4 }

mtxrLTECarrierAggBandwidth OBJECT-TYPE
    SYNTAX Integer32
    UNITS "MHz"
    MAX-ACCESS read-only
    STATUS current
    DESCRIPTION "Bandwidth (LTE carrier aggregation)."
    ::= { mtxrLTECarrierAggEntry 5 }

mtxrLTECarrierAggPhyCellId OBJECT-TYPE
    SYNTAX Integer32
    MAX-ACCESS read-only
    STATUS current
    DESCRIPTION "Phy cell ID (LTE carrier aggregation)."
    ::= { mtxrLTECarrierAggEntry 6 }

mtxrLTECarrierAggRSSI OBJECT-TYPE
    SYNTAX Integer32
    UNITS "dBm"
    MAX-ACCESS read-only
    STATUS current
    DESCRIPTION "RSSI (LTE carrier aggregation)."
    ::= { mtxrLTECarrierAggEntry 7 }

mtxrLTECarrierAggRSRP OBJECT-TYPE
    SYNTAX Integer32
    UNITS "dBm"
    MAX-ACCESS read-only
    STATUS current
    DESCRIPTION "RSRP (LTE carrier aggregation)."
    ::= { mtxrLTECarrierAggEntry 8 }

mtxrLTECarrierAggRSRQ OBJECT-TYPE
    SYNTAX IDiv10
    UNITS "dB"
    MAX-ACCESS read-only
    STATUS current
    DESCRIPTION "RSRQ (LTE carrier aggregation)."
    ::= { mtxrLTECarrierAggEntry 9 }

mtxrLTECarrierAggSINR OBJECT-TYPE
    SYNTAX Integer32
    UNITS "dB"
    MAX-ACCESS read-only
    STATUS current
    DESCRIPTION "SINR (LTE carrier aggregation)."
    ::= { mtxrLTECarrierAggEntry 10 }

mtxrLTECarrierAggSNR OBJECT-TYPE
    SYNTAX Integer32
    UNITS "dB"
    MAX-ACCESS read-only
    STATUS current
    DESCRIPTION "SNR (LTE carrier aggregation)."
    ::= { mtxrLTECarrierAggEntry 11 }

mtxrLTECarrierAggNR OBJECT-TYPE
    SYNTAX TruthValue
    MAX-ACCESS read-only
    STATUS current
    DESCRIPTION "NR (LTE carrier aggregation)."
    ::= { mtxrLTECarrierAggEntry 12 }

mtxrLTECarrierAggUplink OBJECT-TYPE
    SYNTAX TruthValue
    MAX-ACCESS read-only
    STATUS current
    DESCRIPTION "Uplink (LTE carrier aggregation)."
    ::= { mtxrLTECarrierAggEntry 13 }

mtxrLTECarrierAggGroup OBJECT-GROUP
    OBJECTS {
        mtxrLTECarrierAggBand,
        mtxrLTECarrierAggEARFCN,
        mtxrLTECarrierAggBandwidth,
        mtxrLTECarrierAggPhyCellId,
        mtxrLTECarrierAggRSSI,
        mtxrLTECarrierAggRSRP,
        mtxrLTECarrierAggRSRQ,
        mtxrLTECarrierAggSINR,
        mtxrLTECarrierAggSNR,
        mtxrLTECarrierAggNR,
        mtxrLTECarrierAggUplink
    }
    STATUS current
    DESCRIPTION "LTE carrier aggregation information."
    ::= { mtXRouterOsGroups 22 }


-- LTE Modem Firmware ************************************************************

mtxrLteFirmware OBJECT IDENTIFIER ::= { mtxrLTEModem 3 }

mtxrLteFirmwareInstalledVersion OBJECT-TYPE
    SYNTAX      DisplayString (SIZE (0..255))
    MAX-ACCESS  read-only
    STATUS      current
    DESCRIPTION "Firmware version currently installed on the LTE modem."
    ::= { mtxrLteFirmware 1 }

mtxrLteFirmwareLatestVersion OBJECT-TYPE
    SYNTAX      DisplayString (SIZE (0..255))
    MAX-ACCESS  read-only
    STATUS      current
    DESCRIPTION
        "Latest firmware version available for the LTE modem, as determined
         by the most recent successful version check."
    ::= { mtxrLteFirmware 2 }


mtxrLteFirmwareStatus OBJECT-TYPE
    SYNTAX      DisplayString (SIZE (0..255))
    MAX-ACCESS  read-only
    STATUS      current
    DESCRIPTION "Status of the last LTE modem firmware check or upgrade."
    ::= { mtxrLteFirmware 3 }

mtxrLteFirmwareLastChecked OBJECT-TYPE
    SYNTAX      Unsigned32
    UNITS       "seconds since 1970 (epoch)"
    MAX-ACCESS  read-only
    STATUS      current
    DESCRIPTION
        "Unix epoch timestamp indicating when the firmware version was last
         successfully checked online."
    ::= { mtxrLteFirmware 4 }

mtxrLteFirmwareCheckTrigger OBJECT-TYPE
    SYNTAX      Integer32
    MAX-ACCESS  read-write
    STATUS      current
    DESCRIPTION
        "Write the LTE modem device ID to this object to initiate firmware
         version check for that modem."
    ::= { mtxrLteFirmware 5 }

mtxrLteFirmwareInstallTrigger OBJECT-TYPE
    SYNTAX      Integer32
    MAX-ACCESS  read-write
    STATUS      current
    DESCRIPTION
        "Write the LTE modem device ID to this object to initiate firmware
         upgrade for that modem."
    ::= { mtxrLteFirmware 6 }

mtxrLteFirmwareGroup OBJECT-GROUP
    OBJECTS {
        mtxrLteFirmwareInstalledVersion,
        mtxrLteFirmwareLatestVersion,
        mtxrLteFirmwareStatus,
        mtxrLteFirmwareLastChecked,
        mtxrLteFirmwareCheckTrigger,
        mtxrLteFirmwareInstallTrigger
    }
    STATUS current
    DESCRIPTION "LTE modem firmware version and upgrade control."
    ::= { mtXRouterOsGroups 24 }


-- Partition ************************************************************

mtxrPartitionTable OBJECT-TYPE
    SYNTAX SEQUENCE OF MtxrPartitionEntry
    MAX-ACCESS not-accessible
    STATUS current
    DESCRIPTION "System partitions."
    ::= { mtxrPartition 1 }

mtxrPartitionEntry OBJECT-TYPE
    SYNTAX MtxrPartitionEntry
    MAX-ACCESS not-accessible
    STATUS current
    DESCRIPTION "Entry of the system partition table."
    INDEX { mtxrPartitionIndex }
    ::= { mtxrPartitionTable 1 }

MtxrPartitionEntry ::= SEQUENCE {
    mtxrPartitionIndex ObjectIndex,
    mtxrPartitionName DisplayString,
    mtxrPartitionSize Integer32,
    mtxrPartitionVersion DisplayString,
    mtxrPartitionActive BoolValue,
    mtxrPartitionRunning BoolValue
}

mtxrPartitionIndex OBJECT-TYPE
    SYNTAX ObjectIndex
    MAX-ACCESS not-accessible
    STATUS current
    DESCRIPTION
        "Index identifying the row (internal object ID, not the console
         item number)."
    ::= { mtxrPartitionEntry 1 }

mtxrPartitionName OBJECT-TYPE
    SYNTAX DisplayString
    MAX-ACCESS read-only
    STATUS current
    DESCRIPTION "Name (system partition)."
    ::= { mtxrPartitionEntry 2 }

mtxrPartitionSize OBJECT-TYPE
    SYNTAX Integer32
    UNITS "MB"
    MAX-ACCESS read-only
    STATUS current
    DESCRIPTION "Size (system partition)."
    ::= { mtxrPartitionEntry 3 }

mtxrPartitionVersion OBJECT-TYPE
    SYNTAX DisplayString
    MAX-ACCESS read-only
    STATUS current
    DESCRIPTION "Version (system partition)."
    ::= { mtxrPartitionEntry 4 }

mtxrPartitionActive OBJECT-TYPE
    SYNTAX BoolValue
    MAX-ACCESS read-only
    STATUS current
    DESCRIPTION "Active (system partition)."
    ::= { mtxrPartitionEntry 5 }

mtxrPartitionRunning OBJECT-TYPE
    SYNTAX BoolValue
    MAX-ACCESS read-only
    STATUS current
    DESCRIPTION "Running (system partition)."
    ::= { mtxrPartitionEntry 6 }

mtxrPartitionGroup OBJECT-GROUP
    OBJECTS {
        mtxrPartitionName,
        mtxrPartitionSize,
        mtxrPartitionVersion,
        mtxrPartitionActive,
        mtxrPartitionRunning
    }
    STATUS current
    DESCRIPTION "System partitions."
    ::= { mtXRouterOsGroups 20 }

-- OPTICAL *****************************************************************

mtxrOpticalTable OBJECT-TYPE
    SYNTAX SEQUENCE OF MtxrOpticalTableEntry
    MAX-ACCESS not-accessible
    STATUS current
    DESCRIPTION "SFP and GPON information."
    ::= { mtxrOptical 1 }

mtxrOpticalTableEntry OBJECT-TYPE
    SYNTAX MtxrOpticalTableEntry
    MAX-ACCESS not-accessible
    STATUS current
    DESCRIPTION "Entry of the SFP/optical module table."
    INDEX { mtxrOpticalIndex }
    ::= { mtxrOpticalTable 1 }

MtxrOpticalTableEntry ::= SEQUENCE {
        mtxrOpticalIndex ObjectIndex,
        mtxrOpticalName DisplayString,
        mtxrOpticalRxLoss BoolValue,
        mtxrOpticalTxFault BoolValue,
        mtxrOpticalWavelength GDiv100,
        mtxrOpticalTemperature Gauge32,
        mtxrOpticalSupplyVoltage GDiv1000,
        mtxrOpticalTxBiasCurrent Gauge32,
        mtxrOpticalTxPower IDiv1000,
        mtxrOpticalRxPower IDiv1000,
        mtxrOpticalVendorName DisplayString,
        mtxrOpticalVendorSerial DisplayString,
        mtxrOpticalModulePresent BoolValue,
        mtxrOpticalVendorPartNumber DisplayString,
        mtxrOpticalType INTEGER,
        mtxrOpticalConnectorType INTEGER,
        mtxrOpticalLinkLengthCopperOM4 Gauge32,
        mtxrOpticalSupportedRates DisplayString

}

mtxrOpticalGroup OBJECT-GROUP
    OBJECTS {
        mtxrOpticalName,
        mtxrOpticalRxLoss,
        mtxrOpticalTxFault,
        mtxrOpticalWavelength,
        mtxrOpticalTemperature,
        mtxrOpticalSupplyVoltage,
        mtxrOpticalTxBiasCurrent,
        mtxrOpticalTxPower,
        mtxrOpticalRxPower,
        mtxrOpticalVendorName,
        mtxrOpticalVendorSerial,
        mtxrOpticalModulePresent,
        mtxrOpticalVendorPartNumber,
        mtxrOpticalType,
        mtxrOpticalConnectorType,
        mtxrOpticalLinkLengthCopperOM4,
        mtxrOpticalSupportedRates
    }
    STATUS current
    DESCRIPTION "SFP and GPON module diagnostics."
    ::= { mtXRouterOsGroups 6 }

mtxrOpticalIndex OBJECT-TYPE
    SYNTAX ObjectIndex
    MAX-ACCESS not-accessible
    STATUS current
    DESCRIPTION
        "Index identifying the row (internal object ID, not the console
         item number)."
    ::= { mtxrOpticalTableEntry 1 }

mtxrOpticalName OBJECT-TYPE
    SYNTAX DisplayString
    MAX-ACCESS read-only
    STATUS current
    DESCRIPTION "Name (SFP/optical module)."
    ::= { mtxrOpticalTableEntry 2 }

mtxrOpticalRxLoss OBJECT-TYPE
    SYNTAX BoolValue
    MAX-ACCESS read-only
    STATUS current
    DESCRIPTION "Receive loss (SFP/optical module)."
    ::= { mtxrOpticalTableEntry 3 }

mtxrOpticalTxFault OBJECT-TYPE
    SYNTAX BoolValue
    MAX-ACCESS read-only
    STATUS current
    DESCRIPTION "Transmit fault (SFP/optical module)."
    ::= { mtxrOpticalTableEntry 4 }

mtxrOpticalWavelength OBJECT-TYPE
    SYNTAX GDiv100
    UNITS "nm"
    MAX-ACCESS read-only
    STATUS current
    DESCRIPTION "Wavelength (SFP/optical module)."
    ::= { mtxrOpticalTableEntry 5 }

mtxrOpticalTemperature OBJECT-TYPE
    SYNTAX Gauge32
    UNITS "C"
    MAX-ACCESS read-only
    STATUS current
    DESCRIPTION "Temperature (SFP/optical module)."
    ::= { mtxrOpticalTableEntry 6 }

mtxrOpticalSupplyVoltage OBJECT-TYPE
    SYNTAX GDiv1000
    UNITS "V"
    MAX-ACCESS read-only
    STATUS current
    DESCRIPTION "Supply voltage (SFP/optical module)."
    ::= { mtxrOpticalTableEntry 7 }

mtxrOpticalTxBiasCurrent OBJECT-TYPE
    SYNTAX Gauge32
    UNITS "mA"
    MAX-ACCESS read-only
    STATUS current
    DESCRIPTION "Transmit bias current (SFP/optical module)."
    ::= { mtxrOpticalTableEntry 8 }

mtxrOpticalTxPower OBJECT-TYPE
    SYNTAX IDiv1000
    UNITS "dBm"
    MAX-ACCESS read-only
    STATUS current
    DESCRIPTION "Transmit power (SFP/optical module)."
    ::= { mtxrOpticalTableEntry 9 }

mtxrOpticalRxPower OBJECT-TYPE
    SYNTAX IDiv1000
    UNITS "dBm"
    MAX-ACCESS read-only
    STATUS current
    DESCRIPTION "Receive power (SFP/optical module)."
    ::= { mtxrOpticalTableEntry 10 }

mtxrOpticalVendorName OBJECT-TYPE
    SYNTAX DisplayString
    MAX-ACCESS read-only
    STATUS current
    DESCRIPTION "Vendor name (SFP/optical module)."
    ::= { mtxrOpticalTableEntry 11 }

mtxrOpticalVendorSerial OBJECT-TYPE
    SYNTAX DisplayString
    MAX-ACCESS read-only
    STATUS current
    DESCRIPTION "Vendor serial (SFP/optical module)."
    ::= { mtxrOpticalTableEntry 12 }

mtxrOpticalModulePresent OBJECT-TYPE
    SYNTAX BoolValue
    MAX-ACCESS read-only
    STATUS current
    DESCRIPTION "Whether a transceiver module is inserted in the cage."
    ::= { mtxrOpticalTableEntry 13 }

mtxrOpticalVendorPartNumber OBJECT-TYPE
    SYNTAX DisplayString
    MAX-ACCESS read-only
    STATUS current
    DESCRIPTION "Vendor part number of the transceiver module."
    ::= { mtxrOpticalTableEntry 14 }

mtxrOpticalType OBJECT-TYPE
    SYNTAX INTEGER {
        unknown(0),
        gbic(1),
        soldered(2),
        sfp(3),
        dwdmSfp(11),
        qsfp(12),
        qsfpPlus(13),
        qsfp28(17),
        qsfpDD(24),
        qsfpCmis(30)
    }
    MAX-ACCESS read-only
    STATUS current
    DESCRIPTION "Transceiver module type, SFF-8024 identifier value."
    ::= { mtxrOpticalTableEntry 15 }

mtxrOpticalConnectorType OBJECT-TYPE
    SYNTAX INTEGER {
        unknown(0),
        sc(1),
        lc(7),
        opticalPigtail(11),
        mpo1x12(12),
        mpo2x16(13),
        hssdc2(32),
        copperPigtail(33),
        rj45(34),
        noSeparableConnector(35),
        mpo2x12(39),
        mpo1x16(40)
    }
    MAX-ACCESS read-only
    STATUS current
    DESCRIPTION "Transceiver connector type, SFF-8024 connector value."
    ::= { mtxrOpticalTableEntry 16 }

mtxrOpticalLinkLengthCopperOM4 OBJECT-TYPE
    SYNTAX Gauge32
    UNITS "m"
    MAX-ACCESS read-only
    STATUS current
    DESCRIPTION "Supported link length for copper cable or OM4 fiber."
    ::= { mtxrOpticalTableEntry 17 }

mtxrOpticalSupportedRates OBJECT-TYPE
    SYNTAX DisplayString
    MAX-ACCESS read-only
    STATUS current
    DESCRIPTION
        "Comma separated list of link rates supported by the module."
    ::= { mtxrOpticalTableEntry 18 }

-- IPSec *****************************************************************

mtxrIkeSACount OBJECT-TYPE
    SYNTAX Gauge32
    MAX-ACCESS read-only
    STATUS current
    DESCRIPTION "IKE SA count."
    ::= { mtxrIPSec 1 }

mtxrIkeSATable OBJECT-TYPE
    SYNTAX SEQUENCE OF MtxrIkeSATableEntry
    MAX-ACCESS not-accessible
    STATUS current
    DESCRIPTION "IKE SA table."
    ::= { mtxrIPSec 2 }

mtxrIkeSATableEntry OBJECT-TYPE
    SYNTAX MtxrIkeSATableEntry
    MAX-ACCESS not-accessible
    STATUS current
    DESCRIPTION "Entry of the IPsec IKE security association table."
    INDEX {
        mtxrIkeSAIndex
    }
    ::= { mtxrIkeSATable 1 }

MtxrIkeSATableEntry ::= SEQUENCE {
        mtxrIkeSAIndex ObjectIndex,
        mtxrIkeSAInitiatorCookie IsakmpCookie,
        mtxrIkeSAResponderCookie IsakmpCookie,
        mtxrIkeSAResponder BoolValue,
        mtxrIkeSANatt BoolValue,
        mtxrIkeSAVersion Gauge32,
        mtxrIkeSAState INTEGER,
        mtxrIkeSAUptime TimeTicks,
        mtxrIkeSASeen TimeTicks,
        mtxrIkeSAIdentity DisplayString,
        mtxrIkeSAPh2Count Gauge32,
        mtxrIkeSALocalAddressType InetAddressType,
        mtxrIkeSALocalAddress InetAddress,
        mtxrIkeSALocalPort InetPortNumber,
        mtxrIkeSAPeerAddressType InetAddressType,
        mtxrIkeSAPeerAddress InetAddress,
        mtxrIkeSAPeerPort InetPortNumber,
        mtxrIkeSADynamicAddressType InetAddressType,
        mtxrIkeSADynamicAddress InetAddress,
        mtxrIkeSATxBytes Counter64,
        mtxrIkeSARxBytes Counter64,
        mtxrIkeSATxPackets Counter64,
        mtxrIkeSARxPackets Counter64
}

mtxrIkeSAGroup OBJECT-GROUP
    OBJECTS {
        mtxrIkeSACount,
        mtxrIkeSAInitiatorCookie,
        mtxrIkeSAResponderCookie,
        mtxrIkeSAResponder,
        mtxrIkeSANatt,
        mtxrIkeSAVersion,
        mtxrIkeSAState,
        mtxrIkeSAUptime,
        mtxrIkeSASeen,
        mtxrIkeSAIdentity,
        mtxrIkeSAPh2Count,
        mtxrIkeSALocalAddressType,
        mtxrIkeSALocalAddress,
        mtxrIkeSALocalPort,
        mtxrIkeSAPeerAddressType,
        mtxrIkeSAPeerAddress,
        mtxrIkeSAPeerPort,
        mtxrIkeSADynamicAddressType,
        mtxrIkeSADynamicAddress,
        mtxrIkeSATxBytes,
        mtxrIkeSARxBytes,
        mtxrIkeSATxPackets,
        mtxrIkeSARxPackets
    }
    STATUS current
    DESCRIPTION "IPsec IKE security associations."
    ::= { mtXRouterOsGroups 7 }

mtxrIkeSAIndex OBJECT-TYPE
    SYNTAX ObjectIndex
    MAX-ACCESS not-accessible
    STATUS current
    DESCRIPTION
        "Index identifying the row (internal object ID, not the console
         item number)."
    ::= { mtxrIkeSATableEntry 1 }

mtxrIkeSAInitiatorCookie OBJECT-TYPE
    SYNTAX IsakmpCookie
    MAX-ACCESS read-only
    STATUS current
    DESCRIPTION "Initiator SPI."
    ::= { mtxrIkeSATableEntry 2 }

mtxrIkeSAResponderCookie OBJECT-TYPE
    SYNTAX IsakmpCookie
    MAX-ACCESS read-only
    STATUS current
    DESCRIPTION "Responder SPI."
    ::= { mtxrIkeSATableEntry 3 }

mtxrIkeSAResponder OBJECT-TYPE
    SYNTAX BoolValue
    MAX-ACCESS read-only
    STATUS current
    DESCRIPTION "IKE side."
    ::= { mtxrIkeSATableEntry 4 }

mtxrIkeSANatt OBJECT-TYPE
    SYNTAX BoolValue
    MAX-ACCESS read-only
    STATUS current
    DESCRIPTION "NAT is detected."
    ::= { mtxrIkeSATableEntry 5 }

mtxrIkeSAVersion OBJECT-TYPE
    SYNTAX Gauge32
    MAX-ACCESS read-only
    STATUS current
    DESCRIPTION "Protocol version."
    ::= { mtxrIkeSATableEntry 6 }

mtxrIkeSAState OBJECT-TYPE
    SYNTAX INTEGER {
        exchange(1),
        established(2),
        expired(3),
        eap(4)
    }
    MAX-ACCESS read-only
    STATUS current
    DESCRIPTION "State (IPsec IKE security association)."
    ::= { mtxrIkeSATableEntry 7 }

mtxrIkeSAUptime OBJECT-TYPE
    SYNTAX TimeTicks
    MAX-ACCESS read-only
    STATUS current
    DESCRIPTION "Uptime (IPsec IKE security association)."
    ::= { mtxrIkeSATableEntry 8 }

mtxrIkeSASeen OBJECT-TYPE
    SYNTAX TimeTicks
    MAX-ACCESS read-only
    STATUS current
    DESCRIPTION "Time elapsed since last valid IKE packet."
    ::= { mtxrIkeSATableEntry 9 }

mtxrIkeSAIdentity OBJECT-TYPE
    SYNTAX DisplayString
    MAX-ACCESS read-only
    STATUS current
    DESCRIPTION "Peer identity."
    ::= { mtxrIkeSATableEntry 10 }

mtxrIkeSAPh2Count OBJECT-TYPE
    SYNTAX Gauge32
    MAX-ACCESS read-only
    STATUS current
    DESCRIPTION "Total ph2 SA pairs."
    ::= { mtxrIkeSATableEntry 11 }

mtxrIkeSALocalAddressType OBJECT-TYPE
    SYNTAX InetAddressType
    MAX-ACCESS read-only
    STATUS current
    DESCRIPTION "Local address type (IPsec IKE security association)."
    ::= { mtxrIkeSATableEntry 12 }

mtxrIkeSALocalAddress OBJECT-TYPE
    SYNTAX InetAddress
    MAX-ACCESS read-only
    STATUS current
    DESCRIPTION "Local address (IPsec IKE security association)."
    ::= { mtxrIkeSATableEntry 13 }

mtxrIkeSALocalPort OBJECT-TYPE
    SYNTAX InetPortNumber
    MAX-ACCESS read-only
    STATUS current
    DESCRIPTION "Local port (IPsec IKE security association)."
    ::= { mtxrIkeSATableEntry 14 }

mtxrIkeSAPeerAddressType OBJECT-TYPE
    SYNTAX InetAddressType
    MAX-ACCESS read-only
    STATUS current
    DESCRIPTION "Peer address type (IPsec IKE security association)."
    ::= { mtxrIkeSATableEntry 15 }

mtxrIkeSAPeerAddress OBJECT-TYPE
    SYNTAX InetAddress
    MAX-ACCESS read-only
    STATUS current
    DESCRIPTION "Peer address (IPsec IKE security association)."
    ::= { mtxrIkeSATableEntry 16 }

mtxrIkeSAPeerPort OBJECT-TYPE
    SYNTAX InetPortNumber
    MAX-ACCESS read-only
    STATUS current
    DESCRIPTION "Peer port (IPsec IKE security association)."
    ::= { mtxrIkeSATableEntry 17 }

mtxrIkeSADynamicAddressType OBJECT-TYPE
    SYNTAX InetAddressType
    MAX-ACCESS read-only
    STATUS current
    DESCRIPTION "Dynamic address type (IPsec IKE security association)."
    ::= { mtxrIkeSATableEntry 18 }

mtxrIkeSADynamicAddress OBJECT-TYPE
    SYNTAX InetAddress
    MAX-ACCESS read-only
    STATUS current
    DESCRIPTION "Dynamic address allocated by mode config."
    ::= { mtxrIkeSATableEntry 19 }

mtxrIkeSATxBytes OBJECT-TYPE
    SYNTAX Counter64
    UNITS "bytes"
    MAX-ACCESS read-only
    STATUS current
    DESCRIPTION "Ph2 SA tx bytes."
    ::= { mtxrIkeSATableEntry 20 }

mtxrIkeSARxBytes OBJECT-TYPE
    SYNTAX Counter64
    UNITS "bytes"
    MAX-ACCESS read-only
    STATUS current
    DESCRIPTION "Ph2 SA rx bytes."
    ::= { mtxrIkeSATableEntry 21 }

mtxrIkeSATxPackets OBJECT-TYPE
    SYNTAX Counter64
    UNITS "packets"
    MAX-ACCESS read-only
    STATUS current
    DESCRIPTION "Ph2 SA tx packets."
    ::= { mtxrIkeSATableEntry 22 }

mtxrIkeSARxPackets OBJECT-TYPE
    SYNTAX Counter64
    UNITS "packets"
    MAX-ACCESS read-only
    STATUS current
    DESCRIPTION "Ph2 SA rx packets."
    ::= { mtxrIkeSATableEntry 23 }

mtxrWifiCapsman OBJECT IDENTIFIER ::= { mtxrWifi 1 }

mtxrWifiCapsmanEnabled OBJECT-TYPE
    SYNTAX TruthValue
    MAX-ACCESS read-only
    STATUS current
    DESCRIPTION "Indicates whether the Capsman is enabled."
    ::= { mtxrWifiCapsman 1 }

mtxrWifiCapsmanInterfaces OBJECT-TYPE
    SYNTAX DisplayString
    MAX-ACCESS read-only
    STATUS current
    DESCRIPTION "List of interfaces associated with Capsman."
    ::= { mtxrWifiCapsman 2 }

mtxrWifiCapsmanCACertificate OBJECT-TYPE
    SYNTAX DisplayString
    MAX-ACCESS read-only
    STATUS current
    DESCRIPTION "The CA certificate used by Capsman."
    ::= { mtxrWifiCapsman 3 }

mtxrWifiCapsmanCertificate OBJECT-TYPE
    SYNTAX DisplayString
    MAX-ACCESS read-only
    STATUS current
    DESCRIPTION "The local certificate used by Capsman."
    ::= { mtxrWifiCapsman 4 }

mtxrWifiCapsmanRequirePeerCertificate OBJECT-TYPE
    SYNTAX TruthValue
    MAX-ACCESS read-only
    STATUS current
    DESCRIPTION "Whether a peer certificate is required."
    ::= { mtxrWifiCapsman 5 }

mtxrWifiCapsmanPackagePath OBJECT-TYPE
    SYNTAX DisplayString
    MAX-ACCESS read-only
    STATUS current
    DESCRIPTION "Path to the Capsman package directory."
    ::= { mtxrWifiCapsman 6 }

mtxrWifiCapsmanUpgradePolicy OBJECT-TYPE
    SYNTAX Integer32
    MAX-ACCESS read-only
    STATUS current
    DESCRIPTION "Capsman upgrade policy."
    ::= { mtxrWifiCapsman 7 }

mtxrWifiCapsmanGeneratedCaCertificate OBJECT-TYPE
    SYNTAX DisplayString
    MAX-ACCESS read-only
    STATUS current
    DESCRIPTION "Automatically generated CA certificate."
    ::= { mtxrWifiCapsman 8 }

mtxrWifiCapsmanGeneratedCertificate OBJECT-TYPE
    SYNTAX DisplayString
    MAX-ACCESS read-only
    STATUS current
    DESCRIPTION "Automatically generated local certificate."
    ::= { mtxrWifiCapsman 9 }

mtxrWifiCap OBJECT IDENTIFIER ::= { mtxrWifi 2 }

mtxrCapEnabled OBJECT-TYPE
    SYNTAX TruthValue
    MAX-ACCESS read-only
    STATUS current
    DESCRIPTION "Indicates whether the CAP is enabled."
    ::= { mtxrWifiCap 1 }

mtxrCapInterfaces OBJECT-TYPE
    SYNTAX DisplayString
    MAX-ACCESS read-only
    STATUS current
    DESCRIPTION "List of interfaces used by the CAP."
    ::= { mtxrWifiCap 2 }

mtxrCapCertificate OBJECT-TYPE
    SYNTAX DisplayString
    MAX-ACCESS read-only
    STATUS current
    DESCRIPTION "The local certificate used by the CAP."
    ::= { mtxrWifiCap 3 }

mtxrCapCapsManAddresses OBJECT-TYPE
    SYNTAX DisplayString
    MAX-ACCESS read-only
    STATUS current
    DESCRIPTION "Addresses of associated CapsMan controllers."
    ::= { mtxrWifiCap 4 }

mtxrCapCapsManNames OBJECT-TYPE
    SYNTAX DisplayString
    MAX-ACCESS read-only
    STATUS current
    DESCRIPTION "Names of associated CapsMan controllers."
    ::= { mtxrWifiCap 5 }

mtxrCapCapsManCertificateCommonNames OBJECT-TYPE
    SYNTAX DisplayString
    MAX-ACCESS read-only
    STATUS current
    DESCRIPTION "Common names of CapsMan certificates."
    ::= { mtxrWifiCap 6 }

mtxrCapLockToCapsMan OBJECT-TYPE
    SYNTAX TruthValue
    MAX-ACCESS read-only
    STATUS current
    DESCRIPTION "Indicates if the CAP is locked to a specific CapsMan."
    ::= { mtxrWifiCap 7 }

mtxrCapSlavesStatic OBJECT-TYPE
    SYNTAX TruthValue
    MAX-ACCESS read-only
    STATUS current
    DESCRIPTION "Indicates if CAP slaves are set to static mode."
    ::= { mtxrWifiCap 8 }

mtxrCapSlavesDatapath OBJECT-TYPE
    SYNTAX DisplayString
    MAX-ACCESS read-only
    STATUS current
    DESCRIPTION "Datapath configuration of CAP slaves."
    ::= { mtxrWifiCap 9 }

mtxrCapRequestedCertificate OBJECT-TYPE
    SYNTAX DisplayString
    MAX-ACCESS read-only
    STATUS current
    DESCRIPTION "Requested certificate for the CAP."
    ::= { mtxrWifiCap 10 }

mtxrCapLockedCapsManCommonName OBJECT-TYPE
    SYNTAX DisplayString
    MAX-ACCESS read-only
    STATUS current
    DESCRIPTION "Locked CapsMan common name."
    ::= { mtxrWifiCap 11 }

mtxrCapCurrentCapsManAddress OBJECT-TYPE
    SYNTAX DisplayString
    MAX-ACCESS read-only
    STATUS current
    DESCRIPTION "Current CapsMan address being used."
    ::= { mtxrWifiCap 12 }

mtxrCapCurrentCapsManIdentity OBJECT-TYPE
    SYNTAX DisplayString
    MAX-ACCESS read-only
    STATUS current
    DESCRIPTION "Current identity of the connected CapsMan."
    ::= { mtxrWifiCap 13 }

-- Remote Caps *************************************************

mtxrRemoteCapTable OBJECT-TYPE
    SYNTAX SEQUENCE OF MtxrWifiRemoteCapEntry
    MAX-ACCESS not-accessible
    STATUS current
    DESCRIPTION "Table of remote CAP entries."
    ::= { mtxrWifi 3 }

mtxrWifiRemoteCapEntry OBJECT-TYPE
    SYNTAX MtxrWifiRemoteCapEntry
    MAX-ACCESS not-accessible
    STATUS current
    DESCRIPTION "Entry containing remote CAP statistics."
    INDEX { mtxrRemoteCapId }
    ::= { mtxrRemoteCapTable 1 }

MtxrWifiRemoteCapEntry ::= SEQUENCE {
    mtxrRemoteCapId                ObjectIndex,
    mtxrRemoteCapAddress           DisplayString,
    mtxrRemoteCapIdentity          DisplayString,
    mtxrRemoteCapBoardName         DisplayString,
    mtxrRemoteCapSerial            DisplayString,
    mtxrRemoteCapVersion           DisplayString,
    mtxrRemoteCapBaseMac           MacAddress,
    mtxrRemoteCapCommonName        DisplayString,
    mtxrRemoteCapState             DisplayString
}

mtxrRemoteCapId OBJECT-TYPE
    SYNTAX ObjectIndex
    MAX-ACCESS not-accessible
    STATUS current
    DESCRIPTION
        "Index identifying the row (internal object ID, not the console
         item number)."
    ::= { mtxrWifiRemoteCapEntry 1 }

mtxrRemoteCapAddress OBJECT-TYPE
    SYNTAX DisplayString
    MAX-ACCESS read-only
    STATUS current
    DESCRIPTION "IP address of the remote CAP."
    ::= { mtxrWifiRemoteCapEntry 2 }

mtxrRemoteCapIdentity OBJECT-TYPE
    SYNTAX DisplayString
    MAX-ACCESS read-only
    STATUS current
    DESCRIPTION "Identity name of the remote CAP."
    ::= { mtxrWifiRemoteCapEntry 3 }

mtxrRemoteCapBoardName OBJECT-TYPE
    SYNTAX DisplayString
    MAX-ACCESS read-only
    STATUS current
    DESCRIPTION "Board name of the remote CAP."
    ::= { mtxrWifiRemoteCapEntry 4 }

mtxrRemoteCapSerial OBJECT-TYPE
    SYNTAX DisplayString
    MAX-ACCESS read-only
    STATUS current
    DESCRIPTION "Serial number of the remote CAP."
    ::= { mtxrWifiRemoteCapEntry 5 }

mtxrRemoteCapVersion OBJECT-TYPE
    SYNTAX DisplayString
    MAX-ACCESS read-only
    STATUS current
    DESCRIPTION "RouterOS version of the remote CAP."
    ::= { mtxrWifiRemoteCapEntry 6 }

mtxrRemoteCapBaseMac OBJECT-TYPE
    SYNTAX MacAddress
    MAX-ACCESS read-only
    STATUS current
    DESCRIPTION "Base MAC address of the remote CAP."
    ::= { mtxrWifiRemoteCapEntry 7 }

mtxrRemoteCapCommonName OBJECT-TYPE
    SYNTAX DisplayString
    MAX-ACCESS read-only
    STATUS current
    DESCRIPTION "Certificate common name of the remote CAP."
    ::= { mtxrWifiRemoteCapEntry 8 }

mtxrRemoteCapState OBJECT-TYPE
    SYNTAX DisplayString
    MAX-ACCESS read-only
    STATUS current
    DESCRIPTION "State of the remote CAP (e.g., connected, disconnected)."
    ::= { mtxrWifiRemoteCapEntry 9 }

-- Wifi Registration Table *************************************************

mtxrWifiRegistrationTable OBJECT-TYPE
    SYNTAX SEQUENCE OF MtxrWifiRegistrationTableEntry
    MAX-ACCESS not-accessible
    STATUS current
    DESCRIPTION "Table of WiFi registration table entries."
    ::= { mtxrWifi 4 }

mtxrWifiRegistrationTableEntry OBJECT-TYPE
    SYNTAX MtxrWifiRegistrationTableEntry
    MAX-ACCESS not-accessible
    STATUS current
    DESCRIPTION "Entry containing wifi registration statistics."
    INDEX { mtxrWifiRegistrationMacAddress, mtxrWifiRegistrationInterface }
    ::= { mtxrWifiRegistrationTable 1 }

MtxrWifiRegistrationTableEntry ::= SEQUENCE {
    mtxrWifiRegistrationMacAddress         MacAddress,
    mtxrWifiRegistrationInterface          ObjectIndex,
    mtxrWifiRegistrationSsid               DisplayString,
    mtxrWifiRegistrationUptime             TimeTicks,
    mtxrWifiRegistrationLastActivity       Integer32,
    mtxrWifiRegistrationSignal             Integer32,
    mtxrWifiRegistrationAuthType           DisplayString,
    mtxrWifiRegistrationBand               DisplayString,
    mtxrWifiRegistrationTxRate             Gauge32,
    mtxrWifiRegistrationRxRate             Gauge32,
    mtxrWifiRegistrationTxPackets          Counter64,
    mtxrWifiRegistrationRxPackets          Counter64,
    mtxrWifiRegistrationTxBytes            Counter64,
    mtxrWifiRegistrationRxBytes            Counter64,
    mtxrWifiRegistrationTxBitsPerSecond    Integer32,
    mtxrWifiRegistrationRxBitsPerSecond    Integer32,
    mtxrWifiRegistrationVlanId             Integer32,
    mtxrWifiRegistrationAuthorized         TruthValue
}

mtxrWifiRegistrationMacAddress OBJECT-TYPE
    SYNTAX MacAddress
    MAX-ACCESS read-only
    STATUS current
    DESCRIPTION "MAC address of the registered device."
    ::= { mtxrWifiRegistrationTableEntry 1 }

mtxrWifiRegistrationInterface OBJECT-TYPE
    SYNTAX ObjectIndex
    MAX-ACCESS not-accessible
    STATUS current
    DESCRIPTION
        "Index identifying the row (internal object ID, not the console
         item number)."
    ::= { mtxrWifiRegistrationTableEntry 2 }

mtxrWifiRegistrationSsid OBJECT-TYPE
    SYNTAX DisplayString
    MAX-ACCESS read-only
    STATUS current
    DESCRIPTION "SSID of the connected access point."
    ::= { mtxrWifiRegistrationTableEntry 3 }

mtxrWifiRegistrationUptime OBJECT-TYPE
    SYNTAX TimeTicks
    MAX-ACCESS read-only
    STATUS current
    DESCRIPTION "Uptime of the registered connection."
    ::= { mtxrWifiRegistrationTableEntry 4 }

mtxrWifiRegistrationLastActivity OBJECT-TYPE
    SYNTAX Integer32
    MAX-ACCESS read-only
    STATUS current
    DESCRIPTION
        "Time elapsed since the last activity of the registered device."
    ::= { mtxrWifiRegistrationTableEntry 5 }

mtxrWifiRegistrationSignal OBJECT-TYPE
    SYNTAX Integer32
    UNITS "dBm"
    MAX-ACCESS read-only
    STATUS current
    DESCRIPTION "Signal strength of the registered device."
    ::= { mtxrWifiRegistrationTableEntry 6 }

mtxrWifiRegistrationAuthType OBJECT-TYPE
    SYNTAX DisplayString
    MAX-ACCESS read-only
    STATUS current
    DESCRIPTION "Authentication type used by the registered device."
    ::= { mtxrWifiRegistrationTableEntry 7 }

mtxrWifiRegistrationBand OBJECT-TYPE
    SYNTAX DisplayString
    MAX-ACCESS read-only
    STATUS current
    DESCRIPTION "Wireless band used by the registered device."
    ::= { mtxrWifiRegistrationTableEntry 8 }

mtxrWifiRegistrationTxRate OBJECT-TYPE
    SYNTAX Gauge32
    MAX-ACCESS read-only
    STATUS current
    DESCRIPTION "Transmission rate of the registered device."
    ::= { mtxrWifiRegistrationTableEntry 9 }

mtxrWifiRegistrationRxRate OBJECT-TYPE
    SYNTAX Gauge32
    MAX-ACCESS read-only
    STATUS current
    DESCRIPTION "Reception rate of the registered device."
    ::= { mtxrWifiRegistrationTableEntry 10 }

mtxrWifiRegistrationTxPackets OBJECT-TYPE
    SYNTAX Counter64
    UNITS "packets"
    MAX-ACCESS read-only
    STATUS current
    DESCRIPTION "Number of transmitted packets."
    ::= { mtxrWifiRegistrationTableEntry 11 }

mtxrWifiRegistrationRxPackets OBJECT-TYPE
    SYNTAX Counter64
    UNITS "packets"
    MAX-ACCESS read-only
    STATUS current
    DESCRIPTION "Number of received packets."
    ::= { mtxrWifiRegistrationTableEntry 12 }

mtxrWifiRegistrationTxBytes OBJECT-TYPE
    SYNTAX Counter64
    UNITS "bytes"
    MAX-ACCESS read-only
    STATUS current
    DESCRIPTION "Number of transmitted bytes."
    ::= { mtxrWifiRegistrationTableEntry 13 }

mtxrWifiRegistrationRxBytes OBJECT-TYPE
    SYNTAX Counter64
    UNITS "bytes"
    MAX-ACCESS read-only
    STATUS current
    DESCRIPTION "Number of received bytes."
    ::= {mtxrWifiRegistrationTableEntry 14 }

mtxrWifiRegistrationTxBitsPerSecond OBJECT-TYPE
    SYNTAX Integer32
    UNITS "bits per second"
    MAX-ACCESS read-only
    STATUS current
    DESCRIPTION "Transmission rate in bits per second."
    ::= { mtxrWifiRegistrationTableEntry 15 }

mtxrWifiRegistrationRxBitsPerSecond OBJECT-TYPE
    SYNTAX Integer32
    UNITS "bits per second"
    MAX-ACCESS read-only
    STATUS current
    DESCRIPTION "Reception rate in bits per second."
    ::= { mtxrWifiRegistrationTableEntry 16 }

mtxrWifiRegistrationVlanId OBJECT-TYPE
    SYNTAX Integer32
    MAX-ACCESS read-only
    STATUS current
    DESCRIPTION "VLAN ID of the registered device."
    ::= { mtxrWifiRegistrationTableEntry 17 }

mtxrWifiRegistrationAuthorized OBJECT-TYPE
    SYNTAX TruthValue
    MAX-ACCESS read-only
    STATUS current
    DESCRIPTION "Indicates whether the device is authorized."
    ::= { mtxrWifiRegistrationTableEntry 18 }

-- Wifi Interfaces ***********************************************

mtxrWifiInterfaces OBJECT-TYPE
    SYNTAX SEQUENCE OF MtxrWifiInterfacesEntry
    MAX-ACCESS not-accessible
    STATUS current
    DESCRIPTION "Table of WiFi interface entries."
    ::= { mtxrWifi 5 }

mtxrWifiInterfacesEntry OBJECT-TYPE
    SYNTAX MtxrWifiInterfacesEntry
    MAX-ACCESS not-accessible
    STATUS current
    DESCRIPTION "An entry representing WiFi interface."
    INDEX { mtxrWifiInterfacesId }
    ::= { mtxrWifiInterfaces 1 }

MtxrWifiInterfacesEntry ::= SEQUENCE {
    mtxrWifiInterfacesId             ObjectIndex,
    mtxrWifiInterfacesName           DisplayString,
    mtxrWifiInterfacesSsid           DisplayString,
    mtxrWifiInterfacesFreq           DisplayString,
    mtxrWifiInterfacesCurrentChannel DisplayString
}

mtxrWifiInterfacesId OBJECT-TYPE
    SYNTAX      ObjectIndex
    MAX-ACCESS  not-accessible
    STATUS      current
    DESCRIPTION
        "Index identifying the row (internal object ID, not the console
         item number)."
    ::= { mtxrWifiInterfacesEntry 1 }

mtxrWifiInterfacesName OBJECT-TYPE
    SYNTAX      DisplayString
    MAX-ACCESS  read-only
    STATUS      current
    DESCRIPTION "Name of the WiFi interface."
    ::= { mtxrWifiInterfacesEntry 2 }

mtxrWifiInterfacesSsid OBJECT-TYPE
    SYNTAX      DisplayString
    MAX-ACCESS  read-only
    STATUS      current
    DESCRIPTION "SSID associated with the WiFi interface."
    ::= { mtxrWifiInterfacesEntry 3 }

mtxrWifiInterfacesFreq OBJECT-TYPE
    SYNTAX      DisplayString
    MAX-ACCESS  read-only
    STATUS      current
    DESCRIPTION "Frequency used by the WiFi interface."
    ::= { mtxrWifiInterfacesEntry 4 }

mtxrWifiInterfacesCurrentChannel OBJECT-TYPE
    SYNTAX      DisplayString
    MAX-ACCESS  read-only
    STATUS      current
    DESCRIPTION
        "Channel currently in use by the WiFi interface. Empty when the
         interface is not running."
    ::= { mtxrWifiInterfacesEntry 5 }

mtxrWifiGroup OBJECT-GROUP
    OBJECTS {
        mtxrWifiCapsmanEnabled,
        mtxrWifiCapsmanInterfaces,
        mtxrWifiCapsmanCACertificate,
        mtxrWifiCapsmanCertificate,
        mtxrWifiCapsmanRequirePeerCertificate,
        mtxrWifiCapsmanPackagePath,
        mtxrWifiCapsmanUpgradePolicy,
        mtxrWifiCapsmanGeneratedCaCertificate,
        mtxrWifiCapsmanGeneratedCertificate,
        mtxrCapEnabled,
        mtxrCapInterfaces,
        mtxrCapCertificate,
        mtxrCapCapsManAddresses,
        mtxrCapCapsManNames,
        mtxrCapCapsManCertificateCommonNames,
        mtxrCapLockToCapsMan,
        mtxrCapSlavesStatic,
        mtxrCapSlavesDatapath,
        mtxrCapRequestedCertificate,
        mtxrCapLockedCapsManCommonName,
        mtxrCapCurrentCapsManAddress,
        mtxrCapCurrentCapsManIdentity,
        mtxrRemoteCapAddress,
        mtxrRemoteCapIdentity,
        mtxrRemoteCapBoardName,
        mtxrRemoteCapSerial,
        mtxrRemoteCapVersion,
        mtxrRemoteCapBaseMac,
        mtxrRemoteCapCommonName,
        mtxrRemoteCapState,
        mtxrWifiRegistrationMacAddress,
        mtxrWifiRegistrationSsid,
        mtxrWifiRegistrationUptime,
        mtxrWifiRegistrationLastActivity,
        mtxrWifiRegistrationSignal,
        mtxrWifiRegistrationAuthType,
        mtxrWifiRegistrationBand,
        mtxrWifiRegistrationTxRate,
        mtxrWifiRegistrationRxRate,
        mtxrWifiRegistrationTxPackets,
        mtxrWifiRegistrationRxPackets,
        mtxrWifiRegistrationTxBytes,
        mtxrWifiRegistrationRxBytes,
        mtxrWifiRegistrationTxBitsPerSecond,
        mtxrWifiRegistrationRxBitsPerSecond,
        mtxrWifiRegistrationVlanId,
        mtxrWifiRegistrationAuthorized,
        mtxrWifiInterfacesName,
        mtxrWifiInterfacesSsid,
        mtxrWifiInterfacesFreq,
        mtxrWifiInterfacesCurrentChannel
    }
    STATUS current
    DESCRIPTION "WiFi (wifi package) CAPsMAN, CAP, remote CAP, registration and interface information."
    ::= { mtXRouterOsGroups 27 }

mtxrCtGroup OBJECT-GROUP
    OBJECTS {
        mtxrCtTotalEntries,
        mtxrCtIP4Entries,
        mtxrCtIP6Entries
    }
    STATUS current
    DESCRIPTION "Connection tracking counters."
    ::= { mtXRouterOsGroups 28 }

mtxrWlCMRemoteGroup OBJECT-GROUP
    OBJECTS {
        mtxrWlCMState,
        mtxrWlCMChannel,
        mtxrWlCMRemoteName,
        mtxrWlCMRemoteState,
        mtxrWlCMRemoteAddress,
        mtxrWlCMRemoteRadios
    }
    STATUS current
    DESCRIPTION "CAPsMAN interface state and remote CAP list."
    ::= { mtXRouterOsGroups 29 }

-- TRAPS **********************************************************************

mtxrNotifications OBJECT IDENTIFIER ::= { mtxrTraps 0 }

mtxrTrap NOTIFICATION-TYPE
    STATUS  current
    DESCRIPTION "Generic MikroTik trap, sent by the /snmp trap configuration."
    ::= { mtxrNotifications 1 }

mtxrTemperatureException NOTIFICATION-TYPE
    STATUS current
    DESCRIPTION "Mikrotik CPU temperature exception trap"
    ::= { mtxrNotifications 2 }

mtxrTrapGroup NOTIFICATION-GROUP
    NOTIFICATIONS {
        mtxrTrap,
        mtxrTemperatureException
    }
    STATUS current
    DESCRIPTION "Notifications sent by RouterOS."
    ::= { mtXRouterOsGroups 14 }

-- Connection Tracking ********************************************************

mtxrCtTotalEntries OBJECT-TYPE
    SYNTAX Counter32
    MAX-ACCESS read-only
    STATUS current
    DESCRIPTION "Total number of connections."
    ::= { mtxrCT 1 }

mtxrCtIP4Entries OBJECT-TYPE
    SYNTAX Counter32
    MAX-ACCESS read-only
    STATUS current
    DESCRIPTION "Total number of ipv4 connections."
    ::= { mtxrCT 2 }

mtxrCtIP6Entries OBJECT-TYPE
    SYNTAX Counter32
    MAX-ACCESS read-only
    STATUS current
    DESCRIPTION "Total number of ipv6 connections."
    ::= { mtxrCT 3 }

-- ***************************************************************************

END
